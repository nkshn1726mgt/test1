AGGREGATE-MIB DEFINITIONS ::= BEGIN
       IMPORTS
         MODULE-IDENTITY,  experimental, Unsigned32,
         OBJECT-TYPE, Opaque
                    FROM SNMPv2-SMI
         OwnerString
                    FROM RMON-MIB
         RowStatus, StorageType, TEXTUAL-CONVENTION
                    FROM SNMPv2-TC
         MODULE-COMPLIANCE, OBJECT-GROUP
                    FROM SNMPv2-CONF
         SnmpAdminString
                    FROM SNMP-FRAMEWORK-MIB;

     aggrMIB MODULE-IDENTITY
          LAST-UPDATED "200604270000Z"        --  27th April, 2006
          ORGANIZATION "Cyber Solutions Inc. NetMan Working Group"





                  ::= { experimental 123 }

      AggrMOErrorStatus ::= TEXTUAL-CONVENTION
        STATUS       current
        SYNTAX      Opaque (SIZE (0..1024))





      AggrMOValue ::= TEXTUAL-CONVENTION
        STATUS       current
        SYNTAX      Opaque (SIZE (0..1024))

      AggrMOCompressedValue ::= TEXTUAL-CONVENTION
        STATUS       current
        SYNTAX      OCTET STRING (SIZE (0..1024))

      aggrCtlTable OBJECT-TYPE
           SYNTAX  SEQUENCE OF AggrCtlEntry
           MAX-ACCESS  not-accessible
           STATUS current
           ::= {aggrMIB 1}

       aggrCtlEntry OBJECT-TYPE
           SYNTAX  AggrCtlEntry
           MAX-ACCESS  not-accessible
           STATUS  current
           INDEX {aggrCtlEntryID }
           ::= {aggrCtlTable 1 }

       AggrCtlEntry ::= SEQUENCE {
          aggrCtlEntryID
                        SnmpAdminString,
          aggrCtlMOIndex
                        Unsigned32,
          aggrCtlMODescr
                        SnmpAdminString,
          aggrCtlCompressionAlgorithm
                        INTEGER,
          aggrCtlEntryOwner
                        OwnerString,
          aggrCtlEntryStorageType
                        StorageType,
          aggrCtlEntryStatus
                        RowStatus
       }

      aggrCtlEntryID OBJECT-TYPE
           SYNTAX SnmpAdminString (SIZE(1..32))
           MAX-ACCESS not-accessible
           STATUS current
           ::= { aggrCtlEntry 1 }

      aggrCtlMOIndex OBJECT-TYPE
           SYNTAX Unsigned32 (1..2147483647)
           MAX-ACCESS read-create
           STATUS current
           ::= { aggrCtlEntry 2 }

      aggrCtlMODescr OBJECT-TYPE
           SYNTAX SnmpAdminString (SIZE(0..64))
           MAX-ACCESS read-create
           STATUS current





           ::= {aggrCtlEntry 3}

      aggrCtlCompressionAlgorithm OBJECT-TYPE
           SYNTAX INTEGER {
                  none      (1),
                  deflate   (2)
           }
           MAX-ACCESS read-create
           STATUS current
           DEFVAL { none }
           ::= {aggrCtlEntry 4}

      aggrCtlEntryOwner OBJECT-TYPE
           SYNTAX OwnerString
           MAX-ACCESS read-create
           STATUS current
           ::= {aggrCtlEntry 5}

      aggrCtlEntryStorageType OBJECT-TYPE
           SYNTAX StorageType
           MAX-ACCESS read-create
           STATUS current
           ::= {aggrCtlEntry 6}

      aggrCtlEntryStatus OBJECT-TYPE
           SYNTAX RowStatus
           MAX-ACCESS read-create
           STATUS current
           ::= {aggrCtlEntry 7}

      aggrMOTable OBJECT-TYPE
           SYNTAX  SEQUENCE OF AggrMOEntry
           MAX-ACCESS  not-accessible
           STATUS current
           ::= {aggrMIB 2}

       aggrMOEntry OBJECT-TYPE
           SYNTAX  AggrMOEntry
           MAX-ACCESS  not-accessible
           STATUS  current
           INDEX { aggrMOEntryID, aggrMOEntryMOID }
           ::= {aggrMOTable 1 }

       AggrMOEntry ::= SEQUENCE {
          aggrMOEntryID
                        Unsigned32,
          aggrMOEntryMOID
                        Unsigned32,
          aggrMOInstance
                        OBJECT IDENTIFIER,
          aggrMODescr
                        SnmpAdminString,
          aggrMOEntryStorageType
                        StorageType,
          aggrMOEntryStatus
                        RowStatus
       }

      aggrMOEntryID OBJECT-TYPE
           SYNTAX Unsigned32 (1..2147483647)
           MAX-ACCESS not-accessible
           STATUS current
           ::= { aggrMOEntry 1 }

      aggrMOEntryMOID OBJECT-TYPE
           SYNTAX Unsigned32 (1..65535)
           MAX-ACCESS not-accessible
           STATUS current
           ::= { aggrMOEntry 2 }

      aggrMOInstance OBJECT-TYPE
           SYNTAX OBJECT IDENTIFIER
           MAX-ACCESS read-create
           STATUS current





           ::= { aggrMOEntry 3 }

      aggrMODescr OBJECT-TYPE
           SYNTAX SnmpAdminString (SIZE(0..64))
           MAX-ACCESS read-create
           STATUS current
           ::= {aggrMOEntry 4}

      aggrMOEntryStorageType OBJECT-TYPE
           SYNTAX StorageType
           MAX-ACCESS read-create
           STATUS current
           ::= {aggrMOEntry 5}

      aggrMOEntryStatus OBJECT-TYPE
           SYNTAX RowStatus
           MAX-ACCESS read-create
           STATUS current
           ::= {aggrMOEntry 6}






      aggrDataTable OBJECT-TYPE
           SYNTAX  SEQUENCE OF AggrDataEntry
           MAX-ACCESS  not-accessible
           STATUS  current
           ::= {aggrMIB 3}

      aggrDataEntry OBJECT-TYPE
           SYNTAX  AggrDataEntry
           MAX-ACCESS  not-accessible
           STATUS  current
           INDEX {aggrCtlEntryID}
           ::= {aggrDataTable 1 }

      AggrDataEntry ::= SEQUENCE {
         aggrDataRecord
                    AggrMOValue,
         aggrDataRecordCompressed
                    AggrMOCompressedValue,
         aggrDataErrorRecord
                    AggrMOErrorStatus
         }

      aggrDataRecord OBJECT-TYPE
           SYNTAX AggrMOValue
           MAX-ACCESS read-only
           STATUS current
           ::= { aggrDataEntry 1}

      aggrDataRecordCompressed OBJECT-TYPE
           SYNTAX AggrMOCompressedValue





           MAX-ACCESS read-only
           STATUS current
           ::= { aggrDataEntry 2}

      aggrDataErrorRecord OBJECT-TYPE
           SYNTAX AggrMOErrorStatus
           MAX-ACCESS read-only
           STATUS current
           ::= { aggrDataEntry 3}

      aggrConformance OBJECT IDENTIFIER ::= { aggrMIB 4 }
      aggrGroups      OBJECT IDENTIFIER ::= { aggrConformance 1 }
      aggrCompliances OBJECT IDENTIFIER ::= { aggrConformance 2 }

      aggrMibCompliance MODULE-COMPLIANCE
           STATUS  current
           MODULE  -- this module
               MANDATORY-GROUPS { aggrMibBasicGroup }
           ::= { aggrCompliances 1 }

      aggrMibBasicGroup    OBJECT-GROUP
           OBJECTS {
                      aggrCtlMOIndex,
                      aggrCtlMODescr,





                      aggrCtlCompressionAlgorithm,
                      aggrCtlEntryOwner,
                      aggrCtlEntryStorageType,
                      aggrCtlEntryStatus,
                      aggrMOInstance,
                      aggrMODescr,
                      aggrMOEntryStorageType,
                      aggrMOEntryStatus,
                      aggrDataRecord,
                      aggrDataRecordCompressed,
                      aggrDataErrorRecord
          }
           STATUS  current
           ::= { aggrGroups 1 }
      END

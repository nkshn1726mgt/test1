ISCSI-MIB DEFINITIONS  ::= BEGIN

    IMPORTS
    MODULE-IDENTITY, OBJECT-TYPE, OBJECT-IDENTITY, NOTIFICATION-TYPE,
    Unsigned32, Counter32, Counter64, Gauge32,
    mib-2
    FROM SNMPv2-SMI

    TEXTUAL-CONVENTION, TruthValue, RowPointer, TimeStamp, RowStatus,
    AutonomousType, StorageType
    FROM SNMPv2-TC

    MODULE-COMPLIANCE, OBJECT-GROUP, NOTIFICATION-GROUP
    FROM SNMPv2-CONF

    SnmpAdminString
    FROM SNMP-FRAMEWORK-MIB -- RFC 3411

    InetAddressType, InetAddress, InetPortNumber
    FROM INET-ADDRESS-MIB -- RFC 4001
    ;

iscsiMibModule MODULE-IDENTITY
    LAST-UPDATED "201402180000Z" -- February 18, 2014
    ORGANIZATION "IETF STORage Maintenance (STORM) Working Group"



::= { mib-2 142 }

iscsiNotifications OBJECT IDENTIFIER ::= { iscsiMibModule 0 }
iscsiObjects       OBJECT IDENTIFIER ::= { iscsiMibModule 1 }
iscsiConformance   OBJECT IDENTIFIER ::= { iscsiMibModule 2 }
iscsiAdmin         OBJECT IDENTIFIER ::= { iscsiMibModule 3 }


IscsiTransportProtocol ::= TEXTUAL-CONVENTION

    DISPLAY-HINT  "d"
    STATUS        current
    SYNTAX        Unsigned32 (0..255)

IscsiDigestMethod ::= TEXTUAL-CONVENTION
    STATUS        current





    SYNTAX        INTEGER {
                      none(1),
                      other(2),
                      noDigest(3),
                      crc32c(4)
                  }

IscsiName ::= TEXTUAL-CONVENTION
    DISPLAY-HINT  "223t"
    STATUS        current
    SYNTAX        OCTET STRING (SIZE(0 | 16..223))


iscsiDescriptors OBJECT IDENTIFIER ::= { iscsiAdmin 1 }

iscsiHeaderIntegrityTypes OBJECT IDENTIFIER ::= { iscsiDescriptors 1 }

iscsiHdrIntegrityNone OBJECT-IDENTITY
    STATUS      current
::= { iscsiHeaderIntegrityTypes 1 }

iscsiHdrIntegrityCrc32c OBJECT-IDENTITY
    STATUS      current
::= { iscsiHeaderIntegrityTypes 2 }

iscsiDataIntegrityTypes OBJECT IDENTIFIER ::= { iscsiDescriptors 2 }






iscsiDataIntegrityNone OBJECT-IDENTITY
    STATUS      current
::= { iscsiDataIntegrityTypes 1 }

iscsiDataIntegrityCrc32c OBJECT-IDENTITY
    STATUS      current
::= { iscsiDataIntegrityTypes 2 }


iscsiInstance OBJECT IDENTIFIER ::= { iscsiObjects 1 }


iscsiInstanceAttributesTable OBJECT-TYPE
    SYNTAX        SEQUENCE OF IscsiInstanceAttributesEntry
    MAX-ACCESS    not-accessible
    STATUS        current
::= { iscsiInstance 1 }

iscsiInstanceAttributesEntry OBJECT-TYPE
    SYNTAX        IscsiInstanceAttributesEntry
    MAX-ACCESS    not-accessible
    STATUS        current
    INDEX { iscsiInstIndex }
::= { iscsiInstanceAttributesTable 1 }

IscsiInstanceAttributesEntry ::= SEQUENCE {
    iscsiInstIndex                 Unsigned32,
    iscsiInstDescr                 SnmpAdminString,
    iscsiInstVersionMin            Unsigned32,
    iscsiInstVersionMax            Unsigned32,
    iscsiInstVendorID              SnmpAdminString,





    iscsiInstVendorVersion         SnmpAdminString,
    iscsiInstPortalNumber          Unsigned32,
    iscsiInstNodeNumber            Unsigned32,
    iscsiInstSessionNumber         Unsigned32,
    iscsiInstSsnFailures           Counter32,
    iscsiInstLastSsnFailureType    AutonomousType,
    iscsiInstLastSsnRmtNodeName    IscsiName,
    iscsiInstDiscontinuityTime     TimeStamp,
    iscsiInstXNodeArchitecture     SnmpAdminString
}

iscsiInstIndex OBJECT-TYPE
    SYNTAX        Unsigned32 (1..4294967295)
    MAX-ACCESS    not-accessible
    STATUS        current
::= { iscsiInstanceAttributesEntry 1 }

iscsiInstDescr OBJECT-TYPE
    SYNTAX        SnmpAdminString
    MAX-ACCESS    read-only
    STATUS        current

::= { iscsiInstanceAttributesEntry 2 }

iscsiInstVersionMin OBJECT-TYPE
    SYNTAX        Unsigned32 (0..255)
    MAX-ACCESS    read-only
    STATUS        current





::= { iscsiInstanceAttributesEntry 3 }

iscsiInstVersionMax OBJECT-TYPE
    SYNTAX        Unsigned32 (0..255)
    MAX-ACCESS    read-only
    STATUS        current
::= { iscsiInstanceAttributesEntry 4 }

iscsiInstVendorID OBJECT-TYPE
    SYNTAX        SnmpAdminString
    MAX-ACCESS    read-only
    STATUS        current
::= { iscsiInstanceAttributesEntry 5 }

iscsiInstVendorVersion OBJECT-TYPE
    SYNTAX        SnmpAdminString
    MAX-ACCESS    read-only
    STATUS        current
::= { iscsiInstanceAttributesEntry 6 }

iscsiInstPortalNumber OBJECT-TYPE
    SYNTAX        Unsigned32
    UNITS         "transport endpoints"
    MAX-ACCESS    read-only
    STATUS        current
::= { iscsiInstanceAttributesEntry 7 }

iscsiInstNodeNumber OBJECT-TYPE





    SYNTAX        Unsigned32
    UNITS         "iSCSI nodes"
    MAX-ACCESS    read-only
    STATUS        current
::= { iscsiInstanceAttributesEntry 8 }

iscsiInstSessionNumber OBJECT-TYPE
    SYNTAX        Unsigned32
    UNITS         "sessions"
    MAX-ACCESS    read-only
    STATUS        current
::= { iscsiInstanceAttributesEntry 9 }

iscsiInstSsnFailures  OBJECT-TYPE
    SYNTAX        Counter32
    UNITS         "sessions"
    MAX-ACCESS    read-only
    STATUS        current
::= { iscsiInstanceAttributesEntry 10 }

iscsiInstLastSsnFailureType  OBJECT-TYPE
    SYNTAX        AutonomousType
    MAX-ACCESS    read-only
    STATUS        current
::= { iscsiInstanceAttributesEntry 11 }

iscsiInstLastSsnRmtNodeName  OBJECT-TYPE
    SYNTAX        IscsiName





    MAX-ACCESS    read-only
    STATUS        current
::= { iscsiInstanceAttributesEntry 12 }

iscsiInstDiscontinuityTime  OBJECT-TYPE
    SYNTAX        TimeStamp
    MAX-ACCESS    read-only
    STATUS        current
::= { iscsiInstanceAttributesEntry 13 }

iscsiInstXNodeArchitecture OBJECT-TYPE
    SYNTAX        SnmpAdminString
    MAX-ACCESS    read-only
    STATUS        current
::= { iscsiInstanceAttributesEntry 14 }


iscsiInstanceSsnErrorStatsTable OBJECT-TYPE
    SYNTAX        SEQUENCE OF IscsiInstanceSsnErrorStatsEntry
    MAX-ACCESS    not-accessible
    STATUS        current
::= { iscsiInstance 2 }





iscsiInstanceSsnErrorStatsEntry OBJECT-TYPE
    SYNTAX        IscsiInstanceSsnErrorStatsEntry
    MAX-ACCESS    not-accessible
    STATUS        current
    AUGMENTS { iscsiInstanceAttributesEntry }
::= { iscsiInstanceSsnErrorStatsTable 1 }

IscsiInstanceSsnErrorStatsEntry ::= SEQUENCE {
    iscsiInstSsnDigestErrors       Counter32,
    iscsiInstSsnCxnTimeoutErrors   Counter32,
    iscsiInstSsnFormatErrors       Counter32,
    iscsiInstSsnTgtUnmappedErrors  Counter32
}

iscsiInstSsnDigestErrors OBJECT-TYPE
    SYNTAX        Counter32
    UNITS         "sessions"
    MAX-ACCESS    read-only
    STATUS        current
::= { iscsiInstanceSsnErrorStatsEntry 1 }

iscsiInstSsnCxnTimeoutErrors OBJECT-TYPE
    SYNTAX        Counter32
    UNITS         "sessions"
    MAX-ACCESS    read-only
    STATUS        current
::= { iscsiInstanceSsnErrorStatsEntry 2 }

iscsiInstSsnFormatErrors OBJECT-TYPE
    SYNTAX        Counter32
    UNITS         "sessions"





    MAX-ACCESS    read-only
    STATUS        current
::= { iscsiInstanceSsnErrorStatsEntry 3 }

iscsiInstSsnTgtUnmappedErrors OBJECT-TYPE
    SYNTAX        Counter32
    UNITS         "sessions"
    MAX-ACCESS    read-only
    STATUS        current
::= { iscsiInstanceSsnErrorStatsEntry 4 }

iscsiPortal OBJECT IDENTIFIER ::= { iscsiObjects 2 }


iscsiPortalAttributesTable OBJECT-TYPE
    SYNTAX        SEQUENCE OF IscsiPortalAttributesEntry
    MAX-ACCESS    not-accessible
    STATUS        current
::= { iscsiPortal 1 }

iscsiPortalAttributesEntry OBJECT-TYPE
    SYNTAX        IscsiPortalAttributesEntry
    MAX-ACCESS    not-accessible
    STATUS        current
    INDEX { iscsiInstIndex, iscsiPortalIndex  }
::= { iscsiPortalAttributesTable 1 }





IscsiPortalAttributesEntry ::= SEQUENCE {
    iscsiPortalIndex                 Unsigned32,
    iscsiPortalRowStatus             RowStatus,
    iscsiPortalRoles                 BITS,
    iscsiPortalAddrType              InetAddressType,
    iscsiPortalAddr                  InetAddress,
    iscsiPortalProtocol              IscsiTransportProtocol,
    iscsiPortalMaxRecvDataSegLength  Unsigned32,
    iscsiPortalPrimaryHdrDigest      IscsiDigestMethod,
    iscsiPortalPrimaryDataDigest     IscsiDigestMethod,
    iscsiPortalSecondaryHdrDigest    IscsiDigestMethod,
    iscsiPortalSecondaryDataDigest   IscsiDigestMethod,
    iscsiPortalRecvMarker            TruthValue,
    iscsiPortalStorageType           StorageType,
    iscsiPortalDescr                 SnmpAdminString
}

iscsiPortalIndex OBJECT-TYPE
    SYNTAX        Unsigned32 (1..4294967295)
    MAX-ACCESS    not-accessible
    STATUS        current
::= { iscsiPortalAttributesEntry 1 }

iscsiPortalRowStatus OBJECT-TYPE
    SYNTAX        RowStatus
    MAX-ACCESS    read-create
    STATUS        current
::= { iscsiPortalAttributesEntry 2 }

iscsiPortalRoles OBJECT-TYPE





    SYNTAX        BITS {
                      targetTypePortal(0),
                      initiatorTypePortal(1)
                  }
    MAX-ACCESS    read-create
    STATUS        current
::= { iscsiPortalAttributesEntry 3 }

iscsiPortalAddrType OBJECT-TYPE
    SYNTAX        InetAddressType
    MAX-ACCESS    read-create
    STATUS        current
    DEFVAL        { ipv4 }
::= { iscsiPortalAttributesEntry 4 }

iscsiPortalAddr OBJECT-TYPE
    SYNTAX        InetAddress
    MAX-ACCESS    read-create
    STATUS        current
::= { iscsiPortalAttributesEntry 5 }

iscsiPortalProtocol OBJECT-TYPE





    SYNTAX        IscsiTransportProtocol
    MAX-ACCESS    read-create
    STATUS        current
    DEFVAL        { 6 } -- TCP
::= { iscsiPortalAttributesEntry 6 }

iscsiPortalMaxRecvDataSegLength OBJECT-TYPE
    SYNTAX        Unsigned32 (512..16777215)
    UNITS         "bytes"
    MAX-ACCESS    read-create
    STATUS        current
    DEFVAL { 8192 }
::= { iscsiPortalAttributesEntry 7 }

iscsiPortalPrimaryHdrDigest OBJECT-TYPE
    SYNTAX        IscsiDigestMethod
    MAX-ACCESS    read-create
    STATUS        current
    DEFVAL        { crc32c }
::= { iscsiPortalAttributesEntry 8 }

iscsiPortalPrimaryDataDigest OBJECT-TYPE
    SYNTAX        IscsiDigestMethod
    MAX-ACCESS    read-create
    STATUS        current
    DEFVAL        { crc32c }
::= { iscsiPortalAttributesEntry 9 }

iscsiPortalSecondaryHdrDigest OBJECT-TYPE
    SYNTAX        IscsiDigestMethod
    MAX-ACCESS    read-create
    STATUS        current
    DEFVAL        { noDigest }





::= { iscsiPortalAttributesEntry 10 }

iscsiPortalSecondaryDataDigest OBJECT-TYPE
    SYNTAX        IscsiDigestMethod
    MAX-ACCESS    read-create
    STATUS        current
    DEFVAL        { noDigest }
::= { iscsiPortalAttributesEntry 11 }

iscsiPortalRecvMarker OBJECT-TYPE
    SYNTAX        TruthValue
    MAX-ACCESS    read-create
    STATUS        deprecated
    DEFVAL        { false }
::= { iscsiPortalAttributesEntry 12 }

iscsiPortalStorageType OBJECT-TYPE
    SYNTAX        StorageType
    MAX-ACCESS    read-create
    STATUS        current
    DEFVAL        { nonVolatile }
::= { iscsiPortalAttributesEntry 13 }

iscsiPortalDescr OBJECT-TYPE
    SYNTAX        SnmpAdminString
    MAX-ACCESS    read-only
    STATUS        current
::= { iscsiPortalAttributesEntry 14 }

iscsiTargetPortal OBJECT IDENTIFIER ::= { iscsiObjects 3 }


iscsiTgtPortalAttributesTable OBJECT-TYPE
    SYNTAX        SEQUENCE OF IscsiTgtPortalAttributesEntry
    MAX-ACCESS    not-accessible
    STATUS        current
::= { iscsiTargetPortal 1 }

iscsiTgtPortalAttributesEntry OBJECT-TYPE
    SYNTAX        IscsiTgtPortalAttributesEntry
    MAX-ACCESS    not-accessible
    STATUS        current
    INDEX { iscsiInstIndex, iscsiPortalIndex,
            iscsiTgtPortalNodeIndexOrZero  }
::= { iscsiTgtPortalAttributesTable 1 }

IscsiTgtPortalAttributesEntry ::= SEQUENCE {
    iscsiTgtPortalNodeIndexOrZero  Unsigned32,
    iscsiTgtPortalPort             InetPortNumber,
    iscsiTgtPortalTag              Unsigned32
}

iscsiTgtPortalNodeIndexOrZero OBJECT-TYPE
    SYNTAX        Unsigned32 (0..4294967295)
    MAX-ACCESS    not-accessible
    STATUS        current
::= { iscsiTgtPortalAttributesEntry 1 }

iscsiTgtPortalPort OBJECT-TYPE
    SYNTAX        InetPortNumber (1..65535)
    MAX-ACCESS    read-write
    STATUS        current
::= { iscsiTgtPortalAttributesEntry 2 }

iscsiTgtPortalTag OBJECT-TYPE
    SYNTAX        Unsigned32 (1..65535)
    MAX-ACCESS    read-write
    STATUS        current
::= { iscsiTgtPortalAttributesEntry 3 }


iscsiInitiatorPortal OBJECT IDENTIFIER ::= { iscsiObjects 4 }


iscsiIntrPortalAttributesTable OBJECT-TYPE
    SYNTAX        SEQUENCE OF IscsiIntrPortalAttributesEntry
    MAX-ACCESS    not-accessible
    STATUS        current





::= { iscsiInitiatorPortal 1 }

iscsiIntrPortalAttributesEntry OBJECT-TYPE
    SYNTAX        IscsiIntrPortalAttributesEntry
    MAX-ACCESS    not-accessible
    STATUS        current
    INDEX { iscsiInstIndex, iscsiPortalIndex,
            iscsiIntrPortalNodeIndexOrZero  }
::= { iscsiIntrPortalAttributesTable 1 }

IscsiIntrPortalAttributesEntry ::= SEQUENCE {
    iscsiIntrPortalNodeIndexOrZero Unsigned32,
    iscsiIntrPortalTag             Unsigned32
}

iscsiIntrPortalNodeIndexOrZero OBJECT-TYPE
    SYNTAX        Unsigned32 (0..4294967295)
    MAX-ACCESS    not-accessible
    STATUS        current
::= { iscsiIntrPortalAttributesEntry 1 }

iscsiIntrPortalTag OBJECT-TYPE
    SYNTAX        Unsigned32 (1..65535)
    MAX-ACCESS    read-write
    STATUS        current
::= { iscsiIntrPortalAttributesEntry 2 }


iscsiNode OBJECT IDENTIFIER ::= { iscsiObjects 5 }


iscsiNodeAttributesTable OBJECT-TYPE
    SYNTAX        SEQUENCE OF IscsiNodeAttributesEntry
    MAX-ACCESS    not-accessible
    STATUS        current
::= { iscsiNode 1 }

iscsiNodeAttributesEntry OBJECT-TYPE
    SYNTAX        IscsiNodeAttributesEntry
    MAX-ACCESS    not-accessible
    STATUS        current
    INDEX { iscsiInstIndex, iscsiNodeIndex }
::= { iscsiNodeAttributesTable 1 }

IscsiNodeAttributesEntry ::= SEQUENCE {
    iscsiNodeIndex                  Unsigned32,
    iscsiNodeName                   IscsiName,
    iscsiNodeAlias                  SnmpAdminString,
    iscsiNodeRoles                  BITS,
    iscsiNodeTransportType          RowPointer,
    iscsiNodeInitialR2T             TruthValue,
    iscsiNodeImmediateData          TruthValue,
    iscsiNodeMaxOutstandingR2T      Unsigned32,
    iscsiNodeFirstBurstLength       Unsigned32,
    iscsiNodeMaxBurstLength         Unsigned32,
    iscsiNodeMaxConnections         Unsigned32,
    iscsiNodeDataSequenceInOrder    TruthValue,
    iscsiNodeDataPDUInOrder         TruthValue,
    iscsiNodeDefaultTime2Wait       Unsigned32,
    iscsiNodeDefaultTime2Retain     Unsigned32,





    iscsiNodeErrorRecoveryLevel     Unsigned32,
    iscsiNodeDiscontinuityTime      TimeStamp,
    iscsiNodeStorageType            StorageType
}

iscsiNodeIndex OBJECT-TYPE
    SYNTAX        Unsigned32 (1..4294967295)
    MAX-ACCESS    not-accessible
    STATUS        current
::= { iscsiNodeAttributesEntry 1 }

iscsiNodeName OBJECT-TYPE
    SYNTAX        IscsiName
    MAX-ACCESS    read-only
    STATUS        current
::= { iscsiNodeAttributesEntry 2 }

iscsiNodeAlias OBJECT-TYPE
    SYNTAX        SnmpAdminString
    MAX-ACCESS    read-only
    STATUS        current
::= { iscsiNodeAttributesEntry 3 }

iscsiNodeRoles OBJECT-TYPE





    SYNTAX        BITS {
                      targetTypeNode(0),
                      initiatorTypeNode(1)
                  }
    MAX-ACCESS    read-only
    STATUS        current
::= { iscsiNodeAttributesEntry 4 }

iscsiNodeTransportType OBJECT-TYPE
    SYNTAX        RowPointer
    MAX-ACCESS    read-only
    STATUS        current
::= { iscsiNodeAttributesEntry 5 }

iscsiNodeInitialR2T OBJECT-TYPE
    SYNTAX        TruthValue
    MAX-ACCESS    read-only
    STATUS        current





::= { iscsiNodeAttributesEntry 6 }

iscsiNodeImmediateData OBJECT-TYPE
    SYNTAX        TruthValue
    MAX-ACCESS    read-write
    STATUS        current
    DEFVAL        { true }
::= { iscsiNodeAttributesEntry 7 }

iscsiNodeMaxOutstandingR2T OBJECT-TYPE
    SYNTAX        Unsigned32 (1..65535)
    UNITS         "R2Ts"
    MAX-ACCESS    read-write
    STATUS        current
    DEFVAL        { 1 }
::= { iscsiNodeAttributesEntry 8 }

iscsiNodeFirstBurstLength OBJECT-TYPE
    SYNTAX        Unsigned32 (512..16777215)
    UNITS         "bytes"
    MAX-ACCESS    read-write
    STATUS        current
    DEFVAL        { 65536 }
::= { iscsiNodeAttributesEntry 9 }

iscsiNodeMaxBurstLength OBJECT-TYPE
    SYNTAX        Unsigned32 (512..16777215)
    UNITS         "bytes"
    MAX-ACCESS    read-write





    STATUS        current
    DEFVAL        { 262144 }
::= { iscsiNodeAttributesEntry 10 }

iscsiNodeMaxConnections OBJECT-TYPE
    SYNTAX        Unsigned32 (1..65535)
    UNITS         "connections"
    MAX-ACCESS    read-write
    STATUS        current
    DEFVAL        { 1 }
::= { iscsiNodeAttributesEntry 11 }

iscsiNodeDataSequenceInOrder OBJECT-TYPE
    SYNTAX        TruthValue
    MAX-ACCESS    read-write
    STATUS        current
    DEFVAL        { true }
::= { iscsiNodeAttributesEntry 12 }

iscsiNodeDataPDUInOrder OBJECT-TYPE
    SYNTAX        TruthValue
    MAX-ACCESS    read-write
    STATUS        current





    DEFVAL        { true }
::= { iscsiNodeAttributesEntry 13 }

iscsiNodeDefaultTime2Wait OBJECT-TYPE
    SYNTAX        Unsigned32 (0..3600)
    UNITS         "seconds"
    MAX-ACCESS    read-write
    STATUS        current
    DEFVAL        { 2 }
::= { iscsiNodeAttributesEntry 14 }

iscsiNodeDefaultTime2Retain OBJECT-TYPE
    SYNTAX        Unsigned32 (0..3600)
    UNITS         "seconds"
    MAX-ACCESS    read-write
    STATUS        current
    DEFVAL        { 20 }
::= { iscsiNodeAttributesEntry 15 }

iscsiNodeErrorRecoveryLevel OBJECT-TYPE
    SYNTAX        Unsigned32 (0..255)
    MAX-ACCESS    read-write
    STATUS        current
    DEFVAL        { 0 }
::= { iscsiNodeAttributesEntry 16 }

iscsiNodeDiscontinuityTime  OBJECT-TYPE
    SYNTAX        TimeStamp
    MAX-ACCESS    read-only
    STATUS        current
::= { iscsiNodeAttributesEntry 17 }

iscsiNodeStorageType OBJECT-TYPE
    SYNTAX        StorageType
    MAX-ACCESS    read-write
    STATUS        current
    DEFVAL        { volatile }
::= { iscsiNodeAttributesEntry 18 }






iscsiTarget OBJECT IDENTIFIER ::= { iscsiObjects 6 }


iscsiTargetAttributesTable OBJECT-TYPE
    SYNTAX        SEQUENCE OF IscsiTargetAttributesEntry
    MAX-ACCESS    not-accessible
    STATUS        current
::= { iscsiTarget 1 }

iscsiTargetAttributesEntry OBJECT-TYPE
    SYNTAX        IscsiTargetAttributesEntry
    MAX-ACCESS    not-accessible
    STATUS        current
    INDEX { iscsiInstIndex, iscsiNodeIndex }
::= { iscsiTargetAttributesTable 1 }

IscsiTargetAttributesEntry ::= SEQUENCE {
    iscsiTgtLoginFailures           Counter32,
    iscsiTgtLastFailureTime         TimeStamp,
    iscsiTgtLastFailureType         AutonomousType,
    iscsiTgtLastIntrFailureName     IscsiName,
    iscsiTgtLastIntrFailureAddrType InetAddressType,
    iscsiTgtLastIntrFailureAddr     InetAddress,
    iscsiTgtLastIntrFailurePort     InetPortNumber
}

iscsiTgtLoginFailures OBJECT-TYPE
    SYNTAX        Counter32
    UNITS         "failed login attempts"
    MAX-ACCESS    read-only
    STATUS        current
::= { iscsiTargetAttributesEntry 1 }






iscsiTgtLastFailureTime OBJECT-TYPE
    SYNTAX        TimeStamp
    MAX-ACCESS    read-only
    STATUS        current
::= { iscsiTargetAttributesEntry 2 }

iscsiTgtLastFailureType  OBJECT-TYPE
    SYNTAX        AutonomousType
    MAX-ACCESS    read-only
    STATUS        current
::= { iscsiTargetAttributesEntry 3 }

iscsiTgtLastIntrFailureName  OBJECT-TYPE
    SYNTAX        IscsiName
    MAX-ACCESS    read-only
    STATUS        current
::= { iscsiTargetAttributesEntry 4 }

iscsiTgtLastIntrFailureAddrType OBJECT-TYPE
    SYNTAX        InetAddressType
    MAX-ACCESS    read-only
    STATUS        current
::= { iscsiTargetAttributesEntry 5 }

iscsiTgtLastIntrFailureAddr OBJECT-TYPE
    SYNTAX        InetAddress





    MAX-ACCESS    read-only
    STATUS        current
::= { iscsiTargetAttributesEntry 6 }

iscsiTgtLastIntrFailurePort OBJECT-TYPE
    SYNTAX        InetPortNumber
    MAX-ACCESS    read-only
    STATUS        current
::= { iscsiTargetAttributesEntry 7 }


iscsiTargetLoginStatsTable OBJECT-TYPE
    SYNTAX        SEQUENCE OF IscsiTargetLoginStatsEntry
    MAX-ACCESS    not-accessible
    STATUS        current
::= { iscsiTarget 2 }

iscsiTargetLoginStatsEntry OBJECT-TYPE
    SYNTAX        IscsiTargetLoginStatsEntry
    MAX-ACCESS    not-accessible
    STATUS        current
    AUGMENTS { iscsiTargetAttributesEntry }
::= { iscsiTargetLoginStatsTable 1 }

IscsiTargetLoginStatsEntry ::= SEQUENCE {
    iscsiTgtLoginAccepts           Counter32,
    iscsiTgtLoginOtherFails        Counter32,
    iscsiTgtLoginRedirects         Counter32,
    iscsiTgtLoginAuthorizeFails    Counter32,
    iscsiTgtLoginAuthenticateFails Counter32,





    iscsiTgtLoginNegotiateFails    Counter32
}

iscsiTgtLoginAccepts OBJECT-TYPE
    SYNTAX        Counter32
    UNITS         "successful logins"
    MAX-ACCESS    read-only
    STATUS        current
::= { iscsiTargetLoginStatsEntry 1 }

iscsiTgtLoginOtherFails OBJECT-TYPE
    SYNTAX        Counter32
    UNITS         "failed logins"
    MAX-ACCESS    read-only
    STATUS        current
::= { iscsiTargetLoginStatsEntry 2 }

iscsiTgtLoginRedirects OBJECT-TYPE
    SYNTAX        Counter32
    UNITS         "redirected logins"
    MAX-ACCESS    read-only
    STATUS        current
::= { iscsiTargetLoginStatsEntry 3 }

iscsiTgtLoginAuthorizeFails OBJECT-TYPE





    SYNTAX        Counter32
    UNITS         "failed logins"
    MAX-ACCESS    read-only
    STATUS        current
::= { iscsiTargetLoginStatsEntry 4 }

iscsiTgtLoginAuthenticateFails OBJECT-TYPE
    SYNTAX        Counter32
    UNITS         "failed logins"
    MAX-ACCESS    read-only
    STATUS        current
::= { iscsiTargetLoginStatsEntry 5 }

iscsiTgtLoginNegotiateFails OBJECT-TYPE
    SYNTAX        Counter32
    UNITS         "failed logins"
    MAX-ACCESS    read-only
    STATUS        current
::= { iscsiTargetLoginStatsEntry 6 }







iscsiTargetLogoutStatsTable OBJECT-TYPE
    SYNTAX        SEQUENCE OF IscsiTargetLogoutStatsEntry
    MAX-ACCESS    not-accessible
    STATUS        current
::= { iscsiTarget 3 }

iscsiTargetLogoutStatsEntry OBJECT-TYPE
    SYNTAX        IscsiTargetLogoutStatsEntry
    MAX-ACCESS    not-accessible
    STATUS        current
    AUGMENTS { iscsiTargetAttributesEntry }
::= { iscsiTargetLogoutStatsTable 1 }

IscsiTargetLogoutStatsEntry ::= SEQUENCE {
    iscsiTgtLogoutNormals          Counter32,
    iscsiTgtLogoutOthers           Counter32,
    iscsiTgtLogoutCxnClosed        Counter32,
    iscsiTgtLogoutCxnRemoved       Counter32
}

iscsiTgtLogoutNormals OBJECT-TYPE
    SYNTAX        Counter32
    UNITS         "normal logouts"
    MAX-ACCESS    read-only
    STATUS        current
::= { iscsiTargetLogoutStatsEntry 1 }

iscsiTgtLogoutOthers OBJECT-TYPE
    SYNTAX        Counter32
    UNITS         "abnormal logouts"
    MAX-ACCESS    read-only





    STATUS        current
::= { iscsiTargetLogoutStatsEntry 2 }

iscsiTgtLogoutCxnClosed OBJECT-TYPE
    SYNTAX        Counter32
    UNITS         "abnormal logouts"
    MAX-ACCESS    read-only
    STATUS        current
::= { iscsiTargetLogoutStatsEntry 3 }

iscsiTgtLogoutCxnRemoved OBJECT-TYPE
    SYNTAX        Counter32
    UNITS         "abnormal logouts"
    MAX-ACCESS    read-only
    STATUS        current
::= { iscsiTargetLogoutStatsEntry 4 }


iscsiTgtAuthorization OBJECT IDENTIFIER ::= { iscsiObjects 7 }


iscsiTgtAuthAttributesTable OBJECT-TYPE
    SYNTAX        SEQUENCE OF IscsiTgtAuthAttributesEntry
    MAX-ACCESS    not-accessible
    STATUS        current





::= { iscsiTgtAuthorization 1 }

iscsiTgtAuthAttributesEntry OBJECT-TYPE
    SYNTAX        IscsiTgtAuthAttributesEntry
    MAX-ACCESS    not-accessible
    STATUS        current
    INDEX { iscsiInstIndex, iscsiNodeIndex, iscsiTgtAuthIndex }
::= { iscsiTgtAuthAttributesTable 1 }

IscsiTgtAuthAttributesEntry ::= SEQUENCE {
    iscsiTgtAuthIndex              Unsigned32,
    iscsiTgtAuthRowStatus          RowStatus,
    iscsiTgtAuthIdentity           RowPointer,
    iscsiTgtAuthStorageType        StorageType
}

iscsiTgtAuthIndex OBJECT-TYPE
    SYNTAX        Unsigned32 (1..4294967295)
    MAX-ACCESS    not-accessible
    STATUS        current
::= { iscsiTgtAuthAttributesEntry 1 }

iscsiTgtAuthRowStatus OBJECT-TYPE
    SYNTAX        RowStatus
    MAX-ACCESS    read-create
    STATUS        current





::= { iscsiTgtAuthAttributesEntry 2 }

iscsiTgtAuthIdentity OBJECT-TYPE
    SYNTAX        RowPointer
    MAX-ACCESS    read-create
    STATUS        current
::= { iscsiTgtAuthAttributesEntry 3 }

iscsiTgtAuthStorageType OBJECT-TYPE
    SYNTAX        StorageType
    MAX-ACCESS    read-create
    STATUS        current
    DEFVAL        { nonVolatile }
::= { iscsiTgtAuthAttributesEntry 4 }


iscsiInitiator OBJECT IDENTIFIER ::= { iscsiObjects 8 }


iscsiInitiatorAttributesTable OBJECT-TYPE
    SYNTAX        SEQUENCE OF IscsiInitiatorAttributesEntry
    MAX-ACCESS    not-accessible
    STATUS        current
::= { iscsiInitiator 1 }

iscsiInitiatorAttributesEntry OBJECT-TYPE
    SYNTAX        IscsiInitiatorAttributesEntry
    MAX-ACCESS    not-accessible
    STATUS        current
    INDEX  { iscsiInstIndex, iscsiNodeIndex }
::= { iscsiInitiatorAttributesTable 1 }

IscsiInitiatorAttributesEntry ::= SEQUENCE {
    iscsiIntrLoginFailures           Counter32,
    iscsiIntrLastFailureTime         TimeStamp,
    iscsiIntrLastFailureType         AutonomousType,
    iscsiIntrLastTgtFailureName      IscsiName,
    iscsiIntrLastTgtFailureAddrType  InetAddressType,
    iscsiIntrLastTgtFailureAddr      InetAddress,
    iscsiIntrLastTgtFailurePort      InetPortNumber
}

iscsiIntrLoginFailures OBJECT-TYPE
    SYNTAX        Counter32
    UNITS         "failed logins"
    MAX-ACCESS    read-only
    STATUS        current
::= { iscsiInitiatorAttributesEntry 1 }

iscsiIntrLastFailureTime OBJECT-TYPE
    SYNTAX        TimeStamp
    MAX-ACCESS    read-only
    STATUS        current
::= { iscsiInitiatorAttributesEntry 2 }

iscsiIntrLastFailureType  OBJECT-TYPE
    SYNTAX        AutonomousType
    MAX-ACCESS    read-only
    STATUS        current
::= { iscsiInitiatorAttributesEntry 3 }

iscsiIntrLastTgtFailureName  OBJECT-TYPE
    SYNTAX        IscsiName
    MAX-ACCESS    read-only
    STATUS        current
::= { iscsiInitiatorAttributesEntry 4 }

iscsiIntrLastTgtFailureAddrType OBJECT-TYPE
    SYNTAX        InetAddressType
    MAX-ACCESS    read-only
    STATUS        current
::= { iscsiInitiatorAttributesEntry 5 }

iscsiIntrLastTgtFailureAddr OBJECT-TYPE
    SYNTAX        InetAddress
    MAX-ACCESS    read-only
    STATUS        current
::= { iscsiInitiatorAttributesEntry 6 }

iscsiIntrLastTgtFailurePort OBJECT-TYPE
    SYNTAX        InetPortNumber
    MAX-ACCESS    read-only
    STATUS        current
::= { iscsiInitiatorAttributesEntry 7 }


iscsiInitiatorLoginStatsTable OBJECT-TYPE
    SYNTAX        SEQUENCE OF IscsiInitiatorLoginStatsEntry
    MAX-ACCESS    not-accessible
    STATUS        current
::= { iscsiInitiator 2 }

iscsiInitiatorLoginStatsEntry OBJECT-TYPE
    SYNTAX        IscsiInitiatorLoginStatsEntry
    MAX-ACCESS    not-accessible
    STATUS        current
    AUGMENTS { iscsiInitiatorAttributesEntry }
::= { iscsiInitiatorLoginStatsTable 1 }

IscsiInitiatorLoginStatsEntry ::= SEQUENCE {
    iscsiIntrLoginAcceptRsps         Counter32,
    iscsiIntrLoginOtherFailRsps      Counter32,
    iscsiIntrLoginRedirectRsps       Counter32,
    iscsiIntrLoginAuthFailRsps       Counter32,
    iscsiIntrLoginAuthenticateFails  Counter32,
    iscsiIntrLoginNegotiateFails     Counter32,
    iscsiIntrLoginAuthorizeFails     Counter32
}

iscsiIntrLoginAcceptRsps OBJECT-TYPE
    SYNTAX        Counter32
    UNITS         "successful logins"
    MAX-ACCESS    read-only
    STATUS        current
::= { iscsiInitiatorLoginStatsEntry 1 }






iscsiIntrLoginOtherFailRsps OBJECT-TYPE
    SYNTAX        Counter32
    UNITS         "failed logins"
    MAX-ACCESS    read-only
    STATUS        current
::= { iscsiInitiatorLoginStatsEntry 2 }

iscsiIntrLoginRedirectRsps OBJECT-TYPE
    SYNTAX        Counter32
    UNITS         "failed logins"
    MAX-ACCESS    read-only
    STATUS        current
::= { iscsiInitiatorLoginStatsEntry 3 }

iscsiIntrLoginAuthFailRsps OBJECT-TYPE
    SYNTAX        Counter32
    UNITS         "failed logins"
    MAX-ACCESS    read-only
    STATUS        current
::= { iscsiInitiatorLoginStatsEntry 4 }

iscsiIntrLoginAuthenticateFails OBJECT-TYPE
    SYNTAX        Counter32
    UNITS         "failed logins"
    MAX-ACCESS    read-only
    STATUS        current





::= { iscsiInitiatorLoginStatsEntry 5 }

iscsiIntrLoginNegotiateFails OBJECT-TYPE
    SYNTAX        Counter32
    UNITS         "failed logins"
    MAX-ACCESS    read-only
    STATUS        current
::= { iscsiInitiatorLoginStatsEntry 6 }

iscsiIntrLoginAuthorizeFails OBJECT-TYPE
    SYNTAX        Counter32
    UNITS         "failed logins"
    MAX-ACCESS    read-only
    STATUS        current
::= { iscsiInitiatorLoginStatsEntry 7 }


iscsiInitiatorLogoutStatsTable OBJECT-TYPE
    SYNTAX        SEQUENCE OF IscsiInitiatorLogoutStatsEntry
    MAX-ACCESS    not-accessible
    STATUS        current
::= { iscsiInitiator 3 }

iscsiInitiatorLogoutStatsEntry OBJECT-TYPE
    SYNTAX        IscsiInitiatorLogoutStatsEntry
    MAX-ACCESS    not-accessible
    STATUS        current
    AUGMENTS { iscsiInitiatorAttributesEntry }
::= { iscsiInitiatorLogoutStatsTable 1 }

IscsiInitiatorLogoutStatsEntry ::= SEQUENCE {
    iscsiIntrLogoutNormals         Counter32,
    iscsiIntrLogoutOthers          Counter32
}

iscsiIntrLogoutNormals OBJECT-TYPE
    SYNTAX        Counter32
    UNITS         "normal logouts"
    MAX-ACCESS    read-only
    STATUS        current
::= { iscsiInitiatorLogoutStatsEntry 1 }






iscsiIntrLogoutOthers OBJECT-TYPE
    SYNTAX        Counter32
    UNITS         "abnormal logouts"
    MAX-ACCESS    read-only
    STATUS        current

::= { iscsiInitiatorLogoutStatsEntry 2 }


iscsiIntrAuthorization OBJECT IDENTIFIER ::= { iscsiObjects 9 }


iscsiIntrAuthAttributesTable OBJECT-TYPE
    SYNTAX        SEQUENCE OF IscsiIntrAuthAttributesEntry
    MAX-ACCESS    not-accessible
    STATUS        current
::= { iscsiIntrAuthorization 1 }

iscsiIntrAuthAttributesEntry OBJECT-TYPE
    SYNTAX        IscsiIntrAuthAttributesEntry
    MAX-ACCESS    not-accessible
    STATUS        current
    INDEX { iscsiInstIndex, iscsiNodeIndex, iscsiIntrAuthIndex }
::= { iscsiIntrAuthAttributesTable 1 }

IscsiIntrAuthAttributesEntry ::= SEQUENCE {
    iscsiIntrAuthIndex              Unsigned32,
    iscsiIntrAuthRowStatus          RowStatus,
    iscsiIntrAuthIdentity           RowPointer,
    iscsiIntrAuthStorageType        StorageType
}

iscsiIntrAuthIndex OBJECT-TYPE





    SYNTAX        Unsigned32 (1..4294967295)
    MAX-ACCESS    not-accessible
    STATUS        current
::= { iscsiIntrAuthAttributesEntry 1 }

iscsiIntrAuthRowStatus OBJECT-TYPE
    SYNTAX        RowStatus
    MAX-ACCESS    read-create
    STATUS        current
::= { iscsiIntrAuthAttributesEntry 2 }

iscsiIntrAuthIdentity OBJECT-TYPE
    SYNTAX        RowPointer
    MAX-ACCESS    read-create
    STATUS        current
::= { iscsiIntrAuthAttributesEntry 3 }

iscsiIntrAuthStorageType OBJECT-TYPE
    SYNTAX        StorageType
    MAX-ACCESS    read-create
    STATUS        current
    DEFVAL        { nonVolatile }
::= { iscsiIntrAuthAttributesEntry 4 }


iscsiSession OBJECT IDENTIFIER ::= { iscsiObjects 10 }


iscsiSessionAttributesTable OBJECT-TYPE
    SYNTAX        SEQUENCE OF IscsiSessionAttributesEntry
    MAX-ACCESS    not-accessible
    STATUS        current
::= { iscsiSession 1 }

iscsiSessionAttributesEntry OBJECT-TYPE
    SYNTAX        IscsiSessionAttributesEntry
    MAX-ACCESS    not-accessible
    STATUS        current
    INDEX  { iscsiInstIndex, iscsiSsnNodeIndex, iscsiSsnIndex }
::= { iscsiSessionAttributesTable 1 }

IscsiSessionAttributesEntry ::= SEQUENCE {
    iscsiSsnNodeIndex              Unsigned32,
    iscsiSsnIndex                  Unsigned32,
    iscsiSsnDirection              INTEGER,
    iscsiSsnInitiatorName          IscsiName,
    iscsiSsnTargetName             IscsiName,
    iscsiSsnTSIH                   Unsigned32,
    iscsiSsnISID                   OCTET STRING,
    iscsiSsnInitiatorAlias         SnmpAdminString,
    iscsiSsnTargetAlias            SnmpAdminString,
    iscsiSsnInitialR2T             TruthValue,
    iscsiSsnImmediateData          TruthValue,
    iscsiSsnType                   INTEGER,
    iscsiSsnMaxOutstandingR2T      Unsigned32,





    iscsiSsnFirstBurstLength       Unsigned32,
    iscsiSsnMaxBurstLength         Unsigned32,
    iscsiSsnConnectionNumber       Gauge32,
    iscsiSsnAuthIdentity           RowPointer,
    iscsiSsnDataSequenceInOrder    TruthValue,
    iscsiSsnDataPDUInOrder         TruthValue,
    iscsiSsnErrorRecoveryLevel     Unsigned32,
    iscsiSsnDiscontinuityTime      TimeStamp,
    iscsiSsnProtocolLevel          Unsigned32,
    iscsiSsnTaskReporting          BITS
}

iscsiSsnNodeIndex OBJECT-TYPE
    SYNTAX        Unsigned32 (0..4294967295)
    MAX-ACCESS    not-accessible
    STATUS        current
::= { iscsiSessionAttributesEntry 1 }

iscsiSsnIndex OBJECT-TYPE
    SYNTAX        Unsigned32 (1..4294967295)
    MAX-ACCESS    not-accessible
    STATUS        current
::= { iscsiSessionAttributesEntry 2 }

iscsiSsnDirection OBJECT-TYPE
    SYNTAX        INTEGER {
                      inboundSession(1),
                      outboundSession(2)
                  }
    MAX-ACCESS    read-only
    STATUS        current
::= { iscsiSessionAttributesEntry 3 }

iscsiSsnInitiatorName OBJECT-TYPE
    SYNTAX        IscsiName
    MAX-ACCESS    read-only
    STATUS        current
::= { iscsiSessionAttributesEntry 4 }

iscsiSsnTargetName OBJECT-TYPE
    SYNTAX        IscsiName
    MAX-ACCESS    read-only
    STATUS        current
::= { iscsiSessionAttributesEntry 5 }

iscsiSsnTSIH OBJECT-TYPE
    SYNTAX        Unsigned32 (1..65535)
    MAX-ACCESS    read-only
    STATUS        current
::= { iscsiSessionAttributesEntry 6 }

iscsiSsnISID OBJECT-TYPE





    SYNTAX        OCTET STRING (SIZE(6))
    MAX-ACCESS    read-only
    STATUS        current
::= { iscsiSessionAttributesEntry 7 }

iscsiSsnInitiatorAlias OBJECT-TYPE
    SYNTAX        SnmpAdminString
    MAX-ACCESS    read-only
    STATUS        current
::= { iscsiSessionAttributesEntry 8 }

iscsiSsnTargetAlias OBJECT-TYPE
    SYNTAX        SnmpAdminString
    MAX-ACCESS    read-only
    STATUS        current
::= { iscsiSessionAttributesEntry 9 }

iscsiSsnInitialR2T OBJECT-TYPE
    SYNTAX        TruthValue
    MAX-ACCESS    read-only
    STATUS        current
::= { iscsiSessionAttributesEntry 10 }





iscsiSsnImmediateData OBJECT-TYPE
    SYNTAX        TruthValue
    MAX-ACCESS    read-only
    STATUS        current
::= { iscsiSessionAttributesEntry 11 }

iscsiSsnType OBJECT-TYPE

    SYNTAX        INTEGER {
                      normalSession(1),
                      discoverySession(2)
                  }
    MAX-ACCESS    read-only
    STATUS        current
::= { iscsiSessionAttributesEntry 12 }

iscsiSsnMaxOutstandingR2T OBJECT-TYPE
    SYNTAX        Unsigned32 (1..65535)
    UNITS         "R2Ts"
    MAX-ACCESS    read-only
    STATUS        current
::= { iscsiSessionAttributesEntry 13 }

iscsiSsnFirstBurstLength OBJECT-TYPE
    SYNTAX        Unsigned32 (512..16777215)
    UNITS         "bytes"
    MAX-ACCESS    read-only
    STATUS        current
::= { iscsiSessionAttributesEntry 14 }

iscsiSsnMaxBurstLength OBJECT-TYPE
    SYNTAX        Unsigned32 (512..16777215)
    UNITS         "bytes"
    MAX-ACCESS    read-only
    STATUS        current
::= { iscsiSessionAttributesEntry 15 }

iscsiSsnConnectionNumber OBJECT-TYPE
    SYNTAX        Gauge32 (1..65535)
    UNITS         "connections"
    MAX-ACCESS    read-only
    STATUS        current
::= { iscsiSessionAttributesEntry 16 }

iscsiSsnAuthIdentity OBJECT-TYPE
    SYNTAX        RowPointer
    MAX-ACCESS    read-only
    STATUS        current
::= { iscsiSessionAttributesEntry 17 }

 iscsiSsnDataSequenceInOrder OBJECT-TYPE
    SYNTAX        TruthValue
    MAX-ACCESS    read-only
    STATUS        current





::= { iscsiSessionAttributesEntry 18 }

iscsiSsnDataPDUInOrder OBJECT-TYPE
    SYNTAX        TruthValue
    MAX-ACCESS    read-only
    STATUS        current
::= { iscsiSessionAttributesEntry 19 }

iscsiSsnErrorRecoveryLevel OBJECT-TYPE
    SYNTAX        Unsigned32 (0..255)
    MAX-ACCESS    read-only
    STATUS        current
::= { iscsiSessionAttributesEntry 20 }

iscsiSsnDiscontinuityTime  OBJECT-TYPE
    SYNTAX        TimeStamp
    MAX-ACCESS    read-only
    STATUS        current
::= { iscsiSessionAttributesEntry 21 }

iscsiSsnProtocolLevel OBJECT-TYPE
    SYNTAX        Unsigned32 (0..31)
    MAX-ACCESS    read-only
    STATUS        current
    DEFVAL        { 1 }
::= { iscsiSessionAttributesEntry 22 }

iscsiSsnTaskReporting OBJECT-TYPE
    SYNTAX        BITS {
                      taskReportingRfc3720(0),
                      taskReportingResponseFence(1),
                      taskReportingFastAbort(2)
                  }

    MAX-ACCESS    read-only
    STATUS        current
::= { iscsiSessionAttributesEntry 23 }


iscsiSessionStatsTable OBJECT-TYPE
    SYNTAX        SEQUENCE OF IscsiSessionStatsEntry
    MAX-ACCESS    not-accessible
    STATUS        current
::= { iscsiSession 2 }

iscsiSessionStatsEntry OBJECT-TYPE
    SYNTAX        IscsiSessionStatsEntry
    MAX-ACCESS    not-accessible
    STATUS        current
    AUGMENTS { iscsiSessionAttributesEntry }

::= { iscsiSessionStatsTable 1 }

IscsiSessionStatsEntry ::= SEQUENCE {
    iscsiSsnCmdPDUs                Counter32,





    iscsiSsnRspPDUs                Counter32,
    iscsiSsnTxDataOctets           Counter64,
    iscsiSsnRxDataOctets           Counter64,
    iscsiSsnLCTxDataOctets         Counter32,
    iscsiSsnLCRxDataOctets         Counter32,
    iscsiSsnNopReceivedPDUs        Counter32,
    iscsiSsnNopSentPDUs            Counter32
}

iscsiSsnCmdPDUs OBJECT-TYPE
    SYNTAX        Counter32
    UNITS         "PDUs"
    MAX-ACCESS    read-only
    STATUS        current
::= { iscsiSessionStatsEntry 1 }

iscsiSsnRspPDUs OBJECT-TYPE
    SYNTAX        Counter32
    UNITS         "PDUs"
    MAX-ACCESS    read-only
    STATUS        current
::= { iscsiSessionStatsEntry 2 }

iscsiSsnTxDataOctets OBJECT-TYPE
    SYNTAX        Counter64
    UNITS         "octets"
    MAX-ACCESS    read-only
    STATUS        current
::= { iscsiSessionStatsEntry 3 }

iscsiSsnRxDataOctets OBJECT-TYPE
    SYNTAX        Counter64
    UNITS         "octets"
    MAX-ACCESS    read-only
    STATUS        current





::= { iscsiSessionStatsEntry 4 }

iscsiSsnLCTxDataOctets OBJECT-TYPE
    SYNTAX        Counter32
    UNITS         "octets"
    MAX-ACCESS    read-only
    STATUS        current
::= { iscsiSessionStatsEntry 5 }

iscsiSsnLCRxDataOctets OBJECT-TYPE
    SYNTAX        Counter32
    UNITS         "octets"
    MAX-ACCESS    read-only
    STATUS        current
::= { iscsiSessionStatsEntry 6 }

iscsiSsnNopReceivedPDUs OBJECT-TYPE
    SYNTAX        Counter32
    UNITS         "PDUs"
    MAX-ACCESS    read-only
    STATUS        current
::= { iscsiSessionStatsEntry 7 }

iscsiSsnNopSentPDUs OBJECT-TYPE
    SYNTAX        Counter32
    UNITS         "PDUs"
    MAX-ACCESS    read-only
    STATUS        current
::= { iscsiSessionStatsEntry 8 }


iscsiSessionCxnErrorStatsTable OBJECT-TYPE
    SYNTAX        SEQUENCE OF IscsiSessionCxnErrorStatsEntry
    MAX-ACCESS    not-accessible
    STATUS        current
::= { iscsiSession 3 }

iscsiSessionCxnErrorStatsEntry OBJECT-TYPE
    SYNTAX        IscsiSessionCxnErrorStatsEntry
    MAX-ACCESS    not-accessible
    STATUS        current
    AUGMENTS { iscsiSessionAttributesEntry }
::= { iscsiSessionCxnErrorStatsTable 1 }

IscsiSessionCxnErrorStatsEntry ::= SEQUENCE {
    iscsiSsnCxnDigestErrors        Counter32,
    iscsiSsnCxnTimeoutErrors       Counter32
}

iscsiSsnCxnDigestErrors OBJECT-TYPE
    SYNTAX        Counter32
    UNITS         "PDUs"
    MAX-ACCESS    read-only
    STATUS        current
::= { iscsiSessionCxnErrorStatsEntry 1 }

iscsiSsnCxnTimeoutErrors OBJECT-TYPE





    SYNTAX        Counter32
    UNITS         "connections"
    MAX-ACCESS    read-only
    STATUS        current
::= { iscsiSessionCxnErrorStatsEntry 2 }


iscsiConnection OBJECT IDENTIFIER ::= { iscsiObjects 11 }


iscsiConnectionAttributesTable OBJECT-TYPE
    SYNTAX        SEQUENCE OF IscsiConnectionAttributesEntry
    MAX-ACCESS    not-accessible
    STATUS        current
::= { iscsiConnection 1 }

iscsiConnectionAttributesEntry OBJECT-TYPE
    SYNTAX        IscsiConnectionAttributesEntry
    MAX-ACCESS    not-accessible
    STATUS        current
    INDEX  { iscsiInstIndex, iscsiSsnNodeIndex, iscsiSsnIndex,
             iscsiCxnIndex }
::= { iscsiConnectionAttributesTable 1 }

IscsiConnectionAttributesEntry ::= SEQUENCE {
    iscsiCxnIndex                  Unsigned32,
    iscsiCxnCid                    Unsigned32,
    iscsiCxnState                  INTEGER,
    iscsiCxnAddrType               InetAddressType,
    iscsiCxnLocalAddr              InetAddress,
    iscsiCxnProtocol               IscsiTransportProtocol,





    iscsiCxnLocalPort              InetPortNumber,
    iscsiCxnRemoteAddr             InetAddress,
    iscsiCxnRemotePort             InetPortNumber,
    iscsiCxnMaxRecvDataSegLength   Unsigned32,
    iscsiCxnMaxXmitDataSegLength   Unsigned32,
    iscsiCxnHeaderIntegrity        IscsiDigestMethod,
    iscsiCxnDataIntegrity          IscsiDigestMethod,
    iscsiCxnRecvMarker             TruthValue,
    iscsiCxnSendMarker             TruthValue,
    iscsiCxnVersionActive          Unsigned32
}

iscsiCxnIndex OBJECT-TYPE
    SYNTAX        Unsigned32 (1..4294967295)
    MAX-ACCESS    not-accessible
    STATUS        current
::= { iscsiConnectionAttributesEntry 1 }

iscsiCxnCid OBJECT-TYPE
    SYNTAX        Unsigned32 (1..65535)
    MAX-ACCESS    read-only
    STATUS        current
::= { iscsiConnectionAttributesEntry 2 }

iscsiCxnState OBJECT-TYPE
    SYNTAX        INTEGER {
                      login(1),
                      full(2),
                      logout(3)
                  }
    MAX-ACCESS    read-only
    STATUS        current
::= { iscsiConnectionAttributesEntry 3 }

iscsiCxnAddrType OBJECT-TYPE
    SYNTAX        InetAddressType
    MAX-ACCESS    read-only
    STATUS        current
::= { iscsiConnectionAttributesEntry 4 }

iscsiCxnLocalAddr OBJECT-TYPE
    SYNTAX        InetAddress
    MAX-ACCESS    read-only
    STATUS        current
::= { iscsiConnectionAttributesEntry 5 }

iscsiCxnProtocol OBJECT-TYPE
    SYNTAX        IscsiTransportProtocol
    MAX-ACCESS    read-only
    STATUS        current
::= { iscsiConnectionAttributesEntry 6 }

iscsiCxnLocalPort OBJECT-TYPE
    SYNTAX        InetPortNumber
    MAX-ACCESS    read-only
    STATUS        current
::= { iscsiConnectionAttributesEntry 7 }

iscsiCxnRemoteAddr OBJECT-TYPE





    SYNTAX        InetAddress
    MAX-ACCESS    read-only
    STATUS        current
::= { iscsiConnectionAttributesEntry 8 }

iscsiCxnRemotePort OBJECT-TYPE
    SYNTAX        InetPortNumber
    MAX-ACCESS    read-only
    STATUS        current
::= { iscsiConnectionAttributesEntry 9 }

iscsiCxnMaxRecvDataSegLength OBJECT-TYPE
    SYNTAX        Unsigned32 (512..16777215)
    UNITS         "bytes"
    MAX-ACCESS    read-only
    STATUS        current
::= { iscsiConnectionAttributesEntry 10 }

iscsiCxnMaxXmitDataSegLength OBJECT-TYPE
    SYNTAX        Unsigned32 (512..16777215)
    UNITS         "bytes"
    MAX-ACCESS    read-only
    STATUS        current
::= { iscsiConnectionAttributesEntry 11 }

iscsiCxnHeaderIntegrity OBJECT-TYPE
    SYNTAX        IscsiDigestMethod
    MAX-ACCESS    read-only
    STATUS        current
::= { iscsiConnectionAttributesEntry 12 }

iscsiCxnDataIntegrity OBJECT-TYPE
    SYNTAX        IscsiDigestMethod
    MAX-ACCESS    read-only
    STATUS        current
::= { iscsiConnectionAttributesEntry 13 }

iscsiCxnRecvMarker OBJECT-TYPE
    SYNTAX        TruthValue
    MAX-ACCESS    read-only
    STATUS        deprecated
::= { iscsiConnectionAttributesEntry 14 }

iscsiCxnSendMarker OBJECT-TYPE
    SYNTAX        TruthValue
    MAX-ACCESS    read-only
    STATUS        deprecated
::= { iscsiConnectionAttributesEntry 15 }

iscsiCxnVersionActive OBJECT-TYPE
    SYNTAX        Unsigned32 (0..255)
    MAX-ACCESS    read-only
    STATUS        current
::= { iscsiConnectionAttributesEntry 16 }







iscsiTgtLoginFailure NOTIFICATION-TYPE
    OBJECTS {
        iscsiTgtLoginFailures,
        iscsiTgtLastFailureType,
        iscsiTgtLastIntrFailureName,
        iscsiTgtLastIntrFailureAddrType,
        iscsiTgtLastIntrFailureAddr,
        iscsiTgtLastIntrFailurePort
    }
    STATUS current
::= { iscsiNotifications 1 }

iscsiIntrLoginFailure NOTIFICATION-TYPE
    OBJECTS {
        iscsiIntrLoginFailures,
        iscsiIntrLastFailureType,
        iscsiIntrLastTgtFailureName,
        iscsiIntrLastTgtFailureAddrType,
        iscsiIntrLastTgtFailureAddr,
        iscsiIntrLastTgtFailurePort
    }
    STATUS current
::= { iscsiNotifications 2 }

iscsiInstSessionFailure NOTIFICATION-TYPE
    OBJECTS {
        iscsiInstSsnFailures,
        iscsiInstLastSsnFailureType,
        iscsiInstLastSsnRmtNodeName
    }
    STATUS current
::= { iscsiNotifications 3 }



iscsiCompliances OBJECT IDENTIFIER ::= { iscsiConformance 1 }
iscsiGroups      OBJECT IDENTIFIER ::= { iscsiConformance 2 }

iscsiInstanceAttributesGroup OBJECT-GROUP
    OBJECTS {
        iscsiInstDescr,
        iscsiInstVersionMin,
        iscsiInstVersionMax,
        iscsiInstVendorID,
        iscsiInstVendorVersion,
        iscsiInstPortalNumber,
        iscsiInstNodeNumber,
        iscsiInstSessionNumber,
        iscsiInstSsnFailures,
        iscsiInstLastSsnFailureType,
        iscsiInstLastSsnRmtNodeName,
        iscsiInstDiscontinuityTime,
        iscsiInstXNodeArchitecture
    }
    STATUS current
::= { iscsiGroups 1 }

iscsiInstanceSsnErrorStatsGroup OBJECT-GROUP
    OBJECTS {
        iscsiInstSsnDigestErrors,
        iscsiInstSsnCxnTimeoutErrors,
        iscsiInstSsnFormatErrors
    }
    STATUS current
::= { iscsiGroups 2 }






iscsiPortalAttributesGroup OBJECT-GROUP
    OBJECTS {
        iscsiPortalRowStatus,
        iscsiPortalStorageType,
        iscsiPortalRoles,
        iscsiPortalAddrType,
        iscsiPortalAddr,
        iscsiPortalProtocol,
        iscsiPortalMaxRecvDataSegLength,
        iscsiPortalPrimaryHdrDigest,
        iscsiPortalPrimaryDataDigest,
        iscsiPortalSecondaryHdrDigest,
        iscsiPortalSecondaryDataDigest,
        iscsiPortalRecvMarker
    }
    STATUS deprecated
::= { iscsiGroups 3 }

iscsiTgtPortalAttributesGroup OBJECT-GROUP
    OBJECTS {
        iscsiTgtPortalPort,
        iscsiTgtPortalTag
    }
    STATUS current
::= { iscsiGroups 4 }

iscsiIntrPortalAttributesGroup OBJECT-GROUP
    OBJECTS {
        iscsiIntrPortalTag
    }
    STATUS current
::= { iscsiGroups 5 }

iscsiNodeAttributesGroup OBJECT-GROUP
    OBJECTS {





        iscsiNodeName,
        iscsiNodeAlias,
        iscsiNodeRoles,
        iscsiNodeTransportType,
        iscsiNodeInitialR2T,
        iscsiNodeImmediateData,
        iscsiNodeMaxOutstandingR2T,
        iscsiNodeFirstBurstLength,
        iscsiNodeMaxBurstLength,
        iscsiNodeMaxConnections,
        iscsiNodeDataSequenceInOrder,
        iscsiNodeDataPDUInOrder,
        iscsiNodeDefaultTime2Wait,
        iscsiNodeDefaultTime2Retain,
        iscsiNodeErrorRecoveryLevel,
        iscsiNodeDiscontinuityTime,
        iscsiNodeStorageType
    }
    STATUS current
::= { iscsiGroups 6 }

iscsiTargetAttributesGroup OBJECT-GROUP
    OBJECTS {
        iscsiTgtLoginFailures,
        iscsiTgtLastFailureTime,
        iscsiTgtLastFailureType,
        iscsiTgtLastIntrFailureName,
        iscsiTgtLastIntrFailureAddrType,
        iscsiTgtLastIntrFailureAddr
    }
    STATUS current
::= { iscsiGroups 7 }

iscsiTargetLoginStatsGroup OBJECT-GROUP
    OBJECTS {
        iscsiTgtLoginAccepts,
        iscsiTgtLoginOtherFails,
        iscsiTgtLoginRedirects,
        iscsiTgtLoginAuthorizeFails,
        iscsiTgtLoginAuthenticateFails,
        iscsiTgtLoginNegotiateFails
    }





    STATUS current
::= { iscsiGroups 8 }

iscsiTargetLogoutStatsGroup OBJECT-GROUP
    OBJECTS {
        iscsiTgtLogoutNormals,
        iscsiTgtLogoutOthers
    }
    STATUS current
::= { iscsiGroups 9 }

iscsiTargetAuthGroup OBJECT-GROUP
    OBJECTS {
        iscsiTgtAuthRowStatus,
        iscsiTgtAuthStorageType,
        iscsiTgtAuthIdentity
    }
    STATUS current
::= { iscsiGroups 10 }

iscsiInitiatorAttributesGroup OBJECT-GROUP
    OBJECTS {
        iscsiIntrLoginFailures,
        iscsiIntrLastFailureTime,
        iscsiIntrLastFailureType,
        iscsiIntrLastTgtFailureName,
        iscsiIntrLastTgtFailureAddrType,
        iscsiIntrLastTgtFailureAddr
    }
    STATUS current
::= { iscsiGroups 11 }

iscsiInitiatorLoginStatsGroup OBJECT-GROUP
    OBJECTS {
        iscsiIntrLoginAcceptRsps,





        iscsiIntrLoginOtherFailRsps,
        iscsiIntrLoginRedirectRsps,
        iscsiIntrLoginAuthFailRsps,
        iscsiIntrLoginAuthenticateFails,
        iscsiIntrLoginNegotiateFails,
        iscsiIntrLoginAuthorizeFails
    }
    STATUS current
::= { iscsiGroups 12 }

iscsiInitiatorLogoutStatsGroup OBJECT-GROUP
    OBJECTS {
        iscsiIntrLogoutNormals,
        iscsiIntrLogoutOthers
    }
    STATUS current
::= { iscsiGroups 13 }

iscsiInitiatorAuthGroup OBJECT-GROUP
    OBJECTS {
        iscsiIntrAuthRowStatus,
        iscsiIntrAuthStorageType,
        iscsiIntrAuthIdentity
    }
    STATUS current
::= { iscsiGroups 14 }

iscsiSessionAttributesGroup OBJECT-GROUP
    OBJECTS {
        iscsiSsnDirection,
        iscsiSsnInitiatorName,
        iscsiSsnTargetName,
        iscsiSsnTSIH,
        iscsiSsnISID,
        iscsiSsnInitiatorAlias,
        iscsiSsnTargetAlias,
        iscsiSsnInitialR2T,
        iscsiSsnImmediateData,





        iscsiSsnType,
        iscsiSsnMaxOutstandingR2T,
        iscsiSsnFirstBurstLength,
        iscsiSsnMaxBurstLength,
        iscsiSsnConnectionNumber,
        iscsiSsnAuthIdentity,
        iscsiSsnDataSequenceInOrder,
        iscsiSsnDataPDUInOrder,
        iscsiSsnErrorRecoveryLevel,
        iscsiSsnDiscontinuityTime,
        iscsiSsnProtocolLevel,
        iscsiSsnTaskReporting
    }
    STATUS current
::= { iscsiGroups 15 }

iscsiSessionPDUStatsGroup OBJECT-GROUP
    OBJECTS {
        iscsiSsnCmdPDUs,
        iscsiSsnRspPDUs
    }
    STATUS current
::= { iscsiGroups 16 }

iscsiSessionOctetStatsGroup OBJECT-GROUP
    OBJECTS {
        iscsiSsnTxDataOctets,
        iscsiSsnRxDataOctets
    }
    STATUS current
::= { iscsiGroups 17 }

iscsiSessionLCOctetStatsGroup OBJECT-GROUP
    OBJECTS {
        iscsiSsnLCTxDataOctets,
        iscsiSsnLCRxDataOctets
    }
    STATUS current
::= { iscsiGroups 18 }

iscsiSessionCxnErrorStatsGroup OBJECT-GROUP
    OBJECTS {
        iscsiSsnCxnDigestErrors,
        iscsiSsnCxnTimeoutErrors
    }
    STATUS current
::= { iscsiGroups 19 }

iscsiConnectionAttributesGroup OBJECT-GROUP
    OBJECTS {
        iscsiCxnCid,
        iscsiCxnState,
        iscsiCxnProtocol,
        iscsiCxnAddrType,
        iscsiCxnLocalAddr,
        iscsiCxnLocalPort,
        iscsiCxnRemoteAddr,
        iscsiCxnRemotePort,
        iscsiCxnMaxRecvDataSegLength,
        iscsiCxnMaxXmitDataSegLength,
        iscsiCxnHeaderIntegrity,
        iscsiCxnDataIntegrity,
        iscsiCxnRecvMarker,
        iscsiCxnSendMarker,
        iscsiCxnVersionActive
    }
    STATUS deprecated
::= { iscsiGroups 20 }

iscsiTgtLgnNotificationsGroup NOTIFICATION-GROUP
    NOTIFICATIONS {
        iscsiTgtLoginFailure
    }
    STATUS current





::= { iscsiGroups 21 }

iscsiIntrLgnNotificationsGroup NOTIFICATION-GROUP
    NOTIFICATIONS {
        iscsiIntrLoginFailure
    }
    STATUS current
::= { iscsiGroups 22 }

iscsiSsnFlrNotificationsGroup NOTIFICATION-GROUP
    NOTIFICATIONS {
        iscsiInstSessionFailure
    }
    STATUS current
::= { iscsiGroups 23 }

iscsiPortalAttributesGroupV2 OBJECT-GROUP
    OBJECTS {
        iscsiPortalRowStatus,
        iscsiPortalStorageType,
        iscsiPortalRoles,
        iscsiPortalAddrType,
        iscsiPortalAddr,
        iscsiPortalProtocol,
        iscsiPortalMaxRecvDataSegLength,
        iscsiPortalPrimaryHdrDigest,
        iscsiPortalPrimaryDataDigest,
        iscsiPortalSecondaryHdrDigest,
        iscsiPortalSecondaryDataDigest
    }
    STATUS current
::= { iscsiGroups 24 }

iscsiConnectionAttributesGroupV2 OBJECT-GROUP
    OBJECTS {
        iscsiCxnCid,





        iscsiCxnState,
        iscsiCxnProtocol,
        iscsiCxnAddrType,
        iscsiCxnLocalAddr,
        iscsiCxnLocalPort,
        iscsiCxnRemoteAddr,
        iscsiCxnRemotePort,
        iscsiCxnMaxRecvDataSegLength,
        iscsiCxnMaxXmitDataSegLength,
        iscsiCxnHeaderIntegrity,
        iscsiCxnDataIntegrity,
        iscsiCxnVersionActive
    }

    STATUS current
::= { iscsiGroups 25 }

iscsiNewObjectsV2 OBJECT-GROUP
    OBJECTS {
        iscsiInstXNodeArchitecture,
        iscsiSsnTaskReporting,
        iscsiSsnProtocolLevel,
        iscsiSsnNopReceivedPDUs,
        iscsiSsnNopSentPDUs,
        iscsiIntrLastTgtFailurePort,
        iscsiTgtLastIntrFailurePort,
        iscsiPortalDescr,
        iscsiInstSsnTgtUnmappedErrors,
        iscsiTgtLogoutCxnClosed,
        iscsiTgtLogoutCxnRemoved
    }

    STATUS current
::= { iscsiGroups 26 }


iscsiComplianceV1 MODULE-COMPLIANCE
    STATUS deprecated
    MODULE       -- this module
    MANDATORY-GROUPS {
        iscsiInstanceAttributesGroup,
        iscsiInstanceSsnErrorStatsGroup,
        iscsiPortalAttributesGroup,
        iscsiNodeAttributesGroup,
        iscsiSessionAttributesGroup,
        iscsiSessionPDUStatsGroup,
        iscsiSessionCxnErrorStatsGroup,
        iscsiConnectionAttributesGroup,
        iscsiSsnFlrNotificationsGroup
    }


    GROUP iscsiSessionOctetStatsGroup

    GROUP iscsiSessionLCOctetStatsGroup


    GROUP iscsiTgtPortalAttributesGroup

    OBJECT iscsiPortalMaxRecvDataSegLength
    MIN-ACCESS read-only





    OBJECT iscsiNodeStorageType
    MIN-ACCESS read-only
    GROUP iscsiTargetAttributesGroup

    GROUP iscsiTargetLoginStatsGroup

    GROUP iscsiTargetLogoutStatsGroup

    GROUP iscsiTgtLgnNotificationsGroup

    GROUP iscsiTargetAuthGroup


    GROUP iscsiIntrPortalAttributesGroup

    GROUP iscsiInitiatorAttributesGroup

    GROUP iscsiInitiatorLoginStatsGroup

    GROUP iscsiInitiatorLogoutStatsGroup

    GROUP iscsiIntrLgnNotificationsGroup

    GROUP iscsiInitiatorAuthGroup

    OBJECT       iscsiNodeErrorRecoveryLevel
    SYNTAX       Unsigned32 (0..2)

::= { iscsiCompliances 1 }

iscsiComplianceV2 MODULE-COMPLIANCE
    STATUS current
    MODULE       -- this module
    MANDATORY-GROUPS {
        iscsiInstanceAttributesGroup,
        iscsiInstanceSsnErrorStatsGroup,
        iscsiPortalAttributesGroupV2,
        iscsiNodeAttributesGroup,
        iscsiSessionAttributesGroup,
        iscsiSessionPDUStatsGroup,
        iscsiSessionCxnErrorStatsGroup,
        iscsiConnectionAttributesGroupV2,
        iscsiSsnFlrNotificationsGroup
    }






    GROUP iscsiSessionOctetStatsGroup

    GROUP iscsiSessionLCOctetStatsGroup


    GROUP iscsiTgtPortalAttributesGroup

    OBJECT iscsiPortalMaxRecvDataSegLength
    MIN-ACCESS read-only

    OBJECT iscsiNodeStorageType
    MIN-ACCESS read-only

    GROUP iscsiTargetAttributesGroup

    GROUP iscsiTargetLoginStatsGroup

    GROUP iscsiTargetLogoutStatsGroup






    GROUP iscsiTgtLgnNotificationsGroup

    GROUP iscsiTargetAuthGroup


    GROUP iscsiIntrPortalAttributesGroup

    GROUP iscsiInitiatorAttributesGroup

    GROUP iscsiInitiatorLoginStatsGroup

    GROUP iscsiInitiatorLogoutStatsGroup

    GROUP iscsiIntrLgnNotificationsGroup

    GROUP iscsiInitiatorAuthGroup

    OBJECT       iscsiNodeErrorRecoveryLevel
    SYNTAX       Unsigned32 (0..2)





    GROUP iscsiNewObjectsV2

::= { iscsiCompliances 2 }

END

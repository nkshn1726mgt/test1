IANA-MALLOC-MIB DEFINITIONS ::= BEGIN

IMPORTS
    MODULE-IDENTITY, mib-2           FROM SNMPv2-SMI
    TEXTUAL-CONVENTION               FROM SNMPv2-TC;

ianaMallocMIB MODULE-IDENTITY
    LAST-UPDATED "201405220000Z" -- May 22, 2014
    ORGANIZATION "IANA"



    ::= { mib-2 102 } 

IANAscopeSource ::= TEXTUAL-CONVENTION
   STATUS  current
   SYNTAX  INTEGER {
              other(1),  -- none of the following
              manual(2), -- statically configured
              local(3),  -- automatically added by the system,
              mzap(4),   -- MZAP
              madcap(5)  -- MADCAP
           }

IANAmallocRangeSource ::= TEXTUAL-CONVENTION
   STATUS  current
   SYNTAX  INTEGER {
              other(1),  -- none of the following
              manual(2), -- statically configured
              local(3)   -- automatically added by the system,
           }

END

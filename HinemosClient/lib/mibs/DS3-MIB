DS3-MIB DEFINITIONS ::= BEGIN

   IMPORTS
        MODULE-IDENTITY, OBJECT-TYPE,
        NOTIFICATION-TYPE, transmission
             FROM SNMPv2-SMI                    -- [RFC2578]
        DisplayString, TimeStamp, TruthValue
             FROM SNMPv2-TC                     -- [RFC2579]
        MODULE-COMPLIANCE, OBJECT-GROUP,
        NOTIFICATION-GROUP
             FROM SNMPv2-CONF                   -- [RFC2580]
        InterfaceIndex
             FROM IF-MIB                        -- [RFC2863]
        PerfCurrentCount, PerfIntervalCount,
        PerfTotalCount
             FROM PerfHist-TC-MIB;              -- [RFC3593]






   ds3 MODULE-IDENTITY
       LAST-UPDATED "200409080000Z"  -- September 08, 2004
       ORGANIZATION "IETF AToM MIB Working Group"















       ::= { transmission 30 }




   dsx3ConfigTable OBJECT-TYPE
        SYNTAX  SEQUENCE OF Dsx3ConfigEntry
        MAX-ACCESS  not-accessible
        STATUS  current
        ::= { ds3 5 }

   dsx3ConfigEntry OBJECT-TYPE
        SYNTAX  Dsx3ConfigEntry
        MAX-ACCESS  not-accessible
        STATUS  current
        INDEX   { dsx3LineIndex }
        ::= { dsx3ConfigTable 1 }

   Dsx3ConfigEntry ::=
        SEQUENCE {
            dsx3LineIndex                        InterfaceIndex,
            dsx3IfIndex                          InterfaceIndex,
            dsx3TimeElapsed                      INTEGER,
            dsx3ValidIntervals                   INTEGER,
            dsx3LineType                         INTEGER,
            dsx3LineCoding                       INTEGER,
            dsx3SendCode                         INTEGER,
            dsx3CircuitIdentifier                DisplayString,
            dsx3LoopbackConfig                   INTEGER,
            dsx3LineStatus                       INTEGER,
            dsx3TransmitClockSource              INTEGER,
            dsx3InvalidIntervals                 INTEGER,
            dsx3LineLength                       INTEGER,
            dsx3LineStatusLastChange             TimeStamp,





            dsx3LineStatusChangeTrapEnable       INTEGER,
            dsx3LoopbackStatus                   INTEGER,
            dsx3Channelization                   INTEGER,
            dsx3Ds1ForRemoteLoop                 INTEGER

   }

   dsx3LineIndex OBJECT-TYPE
        SYNTAX  InterfaceIndex
        MAX-ACCESS  read-only  -- read-only since originally an

        STATUS  current
        ::= { dsx3ConfigEntry 1 }

   dsx3IfIndex OBJECT-TYPE
        SYNTAX  InterfaceIndex
        MAX-ACCESS  read-only
        STATUS  deprecated
        ::= { dsx3ConfigEntry 2 }

   dsx3TimeElapsed OBJECT-TYPE
        SYNTAX  INTEGER (0..899)
        MAX-ACCESS  read-only
        STATUS  current
        ::= { dsx3ConfigEntry 3 }

   dsx3ValidIntervals OBJECT-TYPE
        SYNTAX  INTEGER (0..96)
        MAX-ACCESS  read-only
        STATUS  current
        ::= { dsx3ConfigEntry 4 }

   dsx3LineType OBJECT-TYPE
        SYNTAX  INTEGER {
                   dsx3other(1),
                   dsx3M23(2),
                   dsx3SYNTRAN(3),
                   dsx3CbitParity(4),
                   dsx3ClearChannel(5),
                   e3other(6),
                   e3Framed(7),
                   e3Plcp(8),
                   dsx3M13(9)
               }
        MAX-ACCESS  read-write
        STATUS  current

        ::= { dsx3ConfigEntry 5 }

   dsx3LineCoding OBJECT-TYPE
        SYNTAX  INTEGER {
                   dsx3Other(1),
                   dsx3B3ZS(2),
                   e3HDB3(3)
               }
        MAX-ACCESS  read-write
        STATUS  current
        ::= { dsx3ConfigEntry 6 }

   dsx3SendCode OBJECT-TYPE





        SYNTAX  INTEGER {
                  dsx3SendNoCode(1),
                  dsx3SendLineCode(2),
                  dsx3SendPayloadCode(3),
                  dsx3SendResetCode(4),
                  dsx3SendDS1LoopCode(5),
                  dsx3SendTestPattern(6)
                  }
        MAX-ACCESS  read-write
        STATUS  current
        ::= { dsx3ConfigEntry 7 }

   dsx3CircuitIdentifier OBJECT-TYPE
        SYNTAX  DisplayString (SIZE (0..255))
        MAX-ACCESS  read-write
        STATUS  current





        ::= { dsx3ConfigEntry 8 }

   dsx3LoopbackConfig OBJECT-TYPE
        SYNTAX  INTEGER {
                    dsx3NoLoop(1),
                    dsx3PayloadLoop(2),
                    dsx3LineLoop(3),
                    dsx3OtherLoop(4),
                    dsx3InwardLoop(5),
                    dsx3DualLoop(6)
                  }
        MAX-ACCESS  read-write
        STATUS  current
        ::= { dsx3ConfigEntry 9 }






   dsx3LineStatus OBJECT-TYPE
        SYNTAX  INTEGER (1..4095)
        MAX-ACCESS  read-only
        STATUS  current
        ::= { dsx3ConfigEntry 10 }

   dsx3TransmitClockSource OBJECT-TYPE
        SYNTAX  INTEGER {
                   loopTiming(1),
                   localTiming(2),
                   throughTiming(3)
               }
        MAX-ACCESS  read-write
        STATUS  current
        ::= { dsx3ConfigEntry 11 }

   dsx3InvalidIntervals OBJECT-TYPE
        SYNTAX  INTEGER (0..96)
        MAX-ACCESS  read-only
        STATUS  current
        ::= { dsx3ConfigEntry 12 }

   dsx3LineLength OBJECT-TYPE
        SYNTAX  INTEGER (0..64000)
        UNITS "meters"
        MAX-ACCESS  read-write
        STATUS  current
        ::= { dsx3ConfigEntry 13 }

   dsx3LineStatusLastChange OBJECT-TYPE
        SYNTAX  TimeStamp
        MAX-ACCESS  read-only
        STATUS  current
        ::= { dsx3ConfigEntry 14 }






   dsx3LineStatusChangeTrapEnable  OBJECT-TYPE
        SYNTAX      INTEGER {
                       enabled(1),
                       disabled(2)
                    }
        MAX-ACCESS  read-write
        STATUS      current
        DEFVAL { disabled }
        ::= { dsx3ConfigEntry 15 }

   dsx3LoopbackStatus  OBJECT-TYPE
        SYNTAX      INTEGER (1..127)
        MAX-ACCESS  read-only
        STATUS      current
        ::= { dsx3ConfigEntry 16 }

   dsx3Channelization  OBJECT-TYPE
        SYNTAX      INTEGER {
                       disabled(1),
                       enabledDs1(2),
                       enabledDs2(3)
                    }
        MAX-ACCESS  read-write
        STATUS      current
        ::= { dsx3ConfigEntry 17 }

   dsx3Ds1ForRemoteLoop  OBJECT-TYPE
        SYNTAX      INTEGER (0..29)
        MAX-ACCESS  read-write
        STATUS      current
        ::= { dsx3ConfigEntry 18 }



   dsx3CurrentTable OBJECT-TYPE
        SYNTAX  SEQUENCE OF Dsx3CurrentEntry
        MAX-ACCESS  not-accessible
        STATUS  current
        ::= { ds3 6 }

   dsx3CurrentEntry OBJECT-TYPE
        SYNTAX  Dsx3CurrentEntry
        MAX-ACCESS  not-accessible
        STATUS  current
        INDEX   { dsx3CurrentIndex }
        ::= { dsx3CurrentTable 1 }

   Dsx3CurrentEntry ::=
        SEQUENCE {
            dsx3CurrentIndex           InterfaceIndex,
            dsx3CurrentPESs            PerfCurrentCount,
            dsx3CurrentPSESs           PerfCurrentCount,
            dsx3CurrentSEFSs           PerfCurrentCount,
            dsx3CurrentUASs            PerfCurrentCount,
            dsx3CurrentLCVs            PerfCurrentCount,





            dsx3CurrentPCVs            PerfCurrentCount,
            dsx3CurrentLESs            PerfCurrentCount,
            dsx3CurrentCCVs            PerfCurrentCount,
            dsx3CurrentCESs            PerfCurrentCount,
            dsx3CurrentCSESs           PerfCurrentCount
       }

   dsx3CurrentIndex OBJECT-TYPE
        SYNTAX  InterfaceIndex
        MAX-ACCESS  read-only  -- read-only since originally an
        STATUS  current
        ::= { dsx3CurrentEntry 1 }

   dsx3CurrentPESs OBJECT-TYPE
        SYNTAX  PerfCurrentCount
        MAX-ACCESS  read-only
        STATUS  current
        ::= { dsx3CurrentEntry 2 }

   dsx3CurrentPSESs OBJECT-TYPE
        SYNTAX  PerfCurrentCount
        MAX-ACCESS  read-only
        STATUS  current
        ::= { dsx3CurrentEntry 3 }

   dsx3CurrentSEFSs OBJECT-TYPE
        SYNTAX  PerfCurrentCount
        MAX-ACCESS  read-only
        STATUS  current
        ::= { dsx3CurrentEntry 4 }






   dsx3CurrentUASs OBJECT-TYPE
        SYNTAX  PerfCurrentCount
        MAX-ACCESS  read-only
        STATUS  current
        ::= { dsx3CurrentEntry 5 }

   dsx3CurrentLCVs OBJECT-TYPE
        SYNTAX  PerfCurrentCount
        MAX-ACCESS  read-only
        STATUS  current
        ::= { dsx3CurrentEntry 6 }

   dsx3CurrentPCVs OBJECT-TYPE
        SYNTAX  PerfCurrentCount
        MAX-ACCESS  read-only
        STATUS  current
        ::= { dsx3CurrentEntry 7 }

   dsx3CurrentLESs OBJECT-TYPE
        SYNTAX  PerfCurrentCount
        MAX-ACCESS  read-only
        STATUS  current
        ::= { dsx3CurrentEntry 8 }

   dsx3CurrentCCVs OBJECT-TYPE
        SYNTAX  PerfCurrentCount
        MAX-ACCESS  read-only
        STATUS  current
        ::= { dsx3CurrentEntry 9 }

   dsx3CurrentCESs OBJECT-TYPE
        SYNTAX  PerfCurrentCount
        MAX-ACCESS  read-only
        STATUS  current
        ::= { dsx3CurrentEntry 10 }

   dsx3CurrentCSESs OBJECT-TYPE
        SYNTAX  PerfCurrentCount
        MAX-ACCESS  read-only
        STATUS  current
        ::= { dsx3CurrentEntry 11 }


   dsx3IntervalTable OBJECT-TYPE
        SYNTAX  SEQUENCE OF Dsx3IntervalEntry
        MAX-ACCESS  not-accessible
        STATUS  current
        ::= { ds3 7 }

   dsx3IntervalEntry OBJECT-TYPE
        SYNTAX  Dsx3IntervalEntry
        MAX-ACCESS  not-accessible
        STATUS  current
        INDEX   { dsx3IntervalIndex, dsx3IntervalNumber }
        ::= { dsx3IntervalTable 1 }

   Dsx3IntervalEntry ::=
        SEQUENCE {
            dsx3IntervalIndex           InterfaceIndex,
            dsx3IntervalNumber          INTEGER,
            dsx3IntervalPESs            PerfIntervalCount,
            dsx3IntervalPSESs           PerfIntervalCount,
            dsx3IntervalSEFSs           PerfIntervalCount,
            dsx3IntervalUASs            PerfIntervalCount,
            dsx3IntervalLCVs            PerfIntervalCount,
            dsx3IntervalPCVs            PerfIntervalCount,
            dsx3IntervalLESs            PerfIntervalCount,





            dsx3IntervalCCVs            PerfIntervalCount,
            dsx3IntervalCESs            PerfIntervalCount,
            dsx3IntervalCSESs           PerfIntervalCount,
            dsx3IntervalValidData       TruthValue
        }

   dsx3IntervalIndex OBJECT-TYPE
        SYNTAX  InterfaceIndex
        MAX-ACCESS  read-only  -- read-only since originally an
        STATUS  current
        ::= { dsx3IntervalEntry 1 }

   dsx3IntervalNumber OBJECT-TYPE
        SYNTAX  INTEGER (1..96)
        MAX-ACCESS  read-only  -- read-only since originally an
        STATUS  current
        ::= { dsx3IntervalEntry 2 }

   dsx3IntervalPESs OBJECT-TYPE
        SYNTAX  PerfIntervalCount
        MAX-ACCESS  read-only
        STATUS  current
        ::= { dsx3IntervalEntry 3 }

   dsx3IntervalPSESs OBJECT-TYPE
        SYNTAX  PerfIntervalCount
        MAX-ACCESS  read-only
        STATUS  current





        ::= { dsx3IntervalEntry 4 }

   dsx3IntervalSEFSs OBJECT-TYPE
        SYNTAX  PerfIntervalCount
        MAX-ACCESS  read-only
        STATUS  current
        ::= { dsx3IntervalEntry 5 }

   dsx3IntervalUASs OBJECT-TYPE
        SYNTAX  PerfIntervalCount
        MAX-ACCESS  read-only
        STATUS  current
        ::= { dsx3IntervalEntry 6 }

   dsx3IntervalLCVs OBJECT-TYPE
        SYNTAX  PerfIntervalCount
        MAX-ACCESS  read-only
        STATUS  current
        ::= { dsx3IntervalEntry 7 }

   dsx3IntervalPCVs OBJECT-TYPE
        SYNTAX  PerfIntervalCount
        MAX-ACCESS  read-only
        STATUS  current
        ::= { dsx3IntervalEntry 8 }

   dsx3IntervalLESs OBJECT-TYPE
        SYNTAX  PerfIntervalCount
        MAX-ACCESS  read-only
        STATUS  current
        ::= { dsx3IntervalEntry 9 }





    dsx3IntervalCCVs OBJECT-TYPE
         SYNTAX  PerfIntervalCount
         MAX-ACCESS  read-only
         STATUS  current
         ::= { dsx3IntervalEntry 10 }

    dsx3IntervalCESs OBJECT-TYPE
         SYNTAX  PerfIntervalCount
         MAX-ACCESS  read-only
         STATUS  current
         ::= { dsx3IntervalEntry 11 }

    dsx3IntervalCSESs OBJECT-TYPE
         SYNTAX  PerfIntervalCount
         MAX-ACCESS  read-only
         STATUS  current
         ::= { dsx3IntervalEntry 12 }

    dsx3IntervalValidData OBJECT-TYPE
         SYNTAX  TruthValue
         MAX-ACCESS read-only
         STATUS current
         ::= { dsx3IntervalEntry 13 }


   dsx3TotalTable OBJECT-TYPE
        SYNTAX  SEQUENCE OF Dsx3TotalEntry
        MAX-ACCESS  not-accessible
        STATUS  current
        ::= { ds3 8 }

   dsx3TotalEntry OBJECT-TYPE
        SYNTAX  Dsx3TotalEntry
        MAX-ACCESS  not-accessible





        STATUS  current
       INDEX   { dsx3TotalIndex }
        ::= { dsx3TotalTable 1 }

   Dsx3TotalEntry ::=
        SEQUENCE {
            dsx3TotalIndex      InterfaceIndex,
            dsx3TotalPESs       PerfTotalCount,
            dsx3TotalPSESs      PerfTotalCount,
            dsx3TotalSEFSs      PerfTotalCount,
            dsx3TotalUASs       PerfTotalCount,
            dsx3TotalLCVs       PerfTotalCount,
            dsx3TotalPCVs       PerfTotalCount,
            dsx3TotalLESs       PerfTotalCount,
            dsx3TotalCCVs       PerfTotalCount,
            dsx3TotalCESs       PerfTotalCount,
            dsx3TotalCSESs      PerfTotalCount
        }

   dsx3TotalIndex OBJECT-TYPE
        SYNTAX  InterfaceIndex
        MAX-ACCESS  read-only  -- read-only since originally an
        STATUS  current
        ::= { dsx3TotalEntry 1 }

   dsx3TotalPESs OBJECT-TYPE
        SYNTAX  PerfTotalCount
        MAX-ACCESS  read-only
        STATUS  current
        ::= { dsx3TotalEntry 2 }

   dsx3TotalPSESs OBJECT-TYPE
        SYNTAX  PerfTotalCount





        MAX-ACCESS  read-only
        STATUS  current
        ::= { dsx3TotalEntry 3 }

   dsx3TotalSEFSs OBJECT-TYPE
        SYNTAX  PerfTotalCount
        MAX-ACCESS  read-only
        STATUS  current
        ::= { dsx3TotalEntry 4 }

   dsx3TotalUASs OBJECT-TYPE
        SYNTAX  PerfTotalCount
        MAX-ACCESS  read-only
        STATUS  current
        ::= { dsx3TotalEntry 5 }

   dsx3TotalLCVs OBJECT-TYPE
        SYNTAX  PerfTotalCount
        MAX-ACCESS  read-only
        STATUS  current
        ::= { dsx3TotalEntry 6 }

   dsx3TotalPCVs OBJECT-TYPE
        SYNTAX  PerfTotalCount
        MAX-ACCESS  read-only
        STATUS  current
        ::= { dsx3TotalEntry 7 }

   dsx3TotalLESs OBJECT-TYPE
        SYNTAX  PerfTotalCount
        MAX-ACCESS  read-only
        STATUS  current
        ::= { dsx3TotalEntry 8 }

   dsx3TotalCCVs OBJECT-TYPE
        SYNTAX  PerfTotalCount
        MAX-ACCESS  read-only
        STATUS  current
        ::= { dsx3TotalEntry 9 }

   dsx3TotalCESs OBJECT-TYPE
        SYNTAX  PerfTotalCount
        MAX-ACCESS  read-only
        STATUS  current
        ::= { dsx3TotalEntry 10 }

   dsx3TotalCSESs OBJECT-TYPE
        SYNTAX  PerfTotalCount
        MAX-ACCESS  read-only
        STATUS  current
        ::= { dsx3TotalEntry 11 }










   dsx3FarEndConfigTable OBJECT-TYPE
        SYNTAX  SEQUENCE OF Dsx3FarEndConfigEntry
        MAX-ACCESS  not-accessible
        STATUS  current
        ::= { ds3 9 }

   dsx3FarEndConfigEntry OBJECT-TYPE
        SYNTAX  Dsx3FarEndConfigEntry
        MAX-ACCESS  not-accessible
        STATUS  current
       INDEX   { dsx3FarEndLineIndex }
        ::= { dsx3FarEndConfigTable 1 }

   Dsx3FarEndConfigEntry ::=
        SEQUENCE {
           dsx3FarEndLineIndex          InterfaceIndex,
           dsx3FarEndEquipCode           DisplayString,
           dsx3FarEndLocationIDCode      DisplayString,
           dsx3FarEndFrameIDCode         DisplayString,
           dsx3FarEndUnitCode            DisplayString,
           dsx3FarEndFacilityIDCode      DisplayString
        }

   dsx3FarEndLineIndex OBJECT-TYPE
        SYNTAX  InterfaceIndex
        MAX-ACCESS  read-only  -- read-only since originally an
        STATUS  current
       ::= { dsx3FarEndConfigEntry 1 }

   dsx3FarEndEquipCode OBJECT-TYPE
        SYNTAX  DisplayString (SIZE (0..10))
        MAX-ACCESS  read-write
        STATUS  current
        ::= { dsx3FarEndConfigEntry 2 }

   dsx3FarEndLocationIDCode OBJECT-TYPE
        SYNTAX  DisplayString (SIZE (0..11))
        MAX-ACCESS  read-write
        STATUS  current
        ::= { dsx3FarEndConfigEntry 3 }

   dsx3FarEndFrameIDCode OBJECT-TYPE
        SYNTAX  DisplayString (SIZE (0..10))
        MAX-ACCESS  read-write
        STATUS  current
        ::= { dsx3FarEndConfigEntry 4 }

   dsx3FarEndUnitCode OBJECT-TYPE
        SYNTAX  DisplayString (SIZE (0..6))
        MAX-ACCESS  read-write
        STATUS  current
        ::= { dsx3FarEndConfigEntry 5 }

   dsx3FarEndFacilityIDCode OBJECT-TYPE





        SYNTAX  DisplayString (SIZE (0..38))
        MAX-ACCESS  read-write
        STATUS  current
        ::= { dsx3FarEndConfigEntry 6 }


   dsx3FarEndCurrentTable OBJECT-TYPE
        SYNTAX  SEQUENCE OF Dsx3FarEndCurrentEntry
        MAX-ACCESS  not-accessible
        STATUS  current
        ::= { ds3 10 }

   dsx3FarEndCurrentEntry OBJECT-TYPE
        SYNTAX  Dsx3FarEndCurrentEntry
        MAX-ACCESS  not-accessible
        STATUS  current
        INDEX   { dsx3FarEndCurrentIndex }
        ::= { dsx3FarEndCurrentTable 1 }

   Dsx3FarEndCurrentEntry ::=
        SEQUENCE {
            dsx3FarEndCurrentIndex        InterfaceIndex,
            dsx3FarEndTimeElapsed         INTEGER,
            dsx3FarEndValidIntervals      INTEGER,
            dsx3FarEndCurrentCESs         PerfCurrentCount,
            dsx3FarEndCurrentCSESs        PerfCurrentCount,
            dsx3FarEndCurrentCCVs         PerfCurrentCount,
            dsx3FarEndCurrentUASs         PerfCurrentCount,
            dsx3FarEndInvalidIntervals    INTEGER
       }

    dsx3FarEndCurrentIndex OBJECT-TYPE
        SYNTAX  InterfaceIndex
        MAX-ACCESS  read-only  -- read-only since originally an





        STATUS  current
        ::= { dsx3FarEndCurrentEntry 1 }

   dsx3FarEndTimeElapsed OBJECT-TYPE
        SYNTAX  INTEGER (0..899)
        MAX-ACCESS  read-only
        STATUS  current
        ::= { dsx3FarEndCurrentEntry 2 }

   dsx3FarEndValidIntervals OBJECT-TYPE
        SYNTAX  INTEGER (0..96)
        MAX-ACCESS  read-only
        STATUS  current
        ::= { dsx3FarEndCurrentEntry 3 }

   dsx3FarEndCurrentCESs OBJECT-TYPE
        SYNTAX  PerfCurrentCount
        MAX-ACCESS  read-only
        STATUS  current
        ::= { dsx3FarEndCurrentEntry 4 }






   dsx3FarEndCurrentCSESs OBJECT-TYPE
        SYNTAX  PerfCurrentCount
        MAX-ACCESS  read-only
        STATUS  current
        ::= { dsx3FarEndCurrentEntry 5 }

   dsx3FarEndCurrentCCVs OBJECT-TYPE
        SYNTAX  PerfCurrentCount
        MAX-ACCESS  read-only
        STATUS  current
        ::= { dsx3FarEndCurrentEntry 6 }

   dsx3FarEndCurrentUASs OBJECT-TYPE
        SYNTAX  PerfCurrentCount
        MAX-ACCESS  read-only
        STATUS  current
        ::= { dsx3FarEndCurrentEntry 7 }

   dsx3FarEndInvalidIntervals OBJECT-TYPE
        SYNTAX  INTEGER (0..96)
        MAX-ACCESS  read-only
        STATUS  current
        ::= { dsx3FarEndCurrentEntry 8 }


   dsx3FarEndIntervalTable OBJECT-TYPE
        SYNTAX  SEQUENCE OF Dsx3FarEndIntervalEntry
        MAX-ACCESS  not-accessible
        STATUS  current
        ::= { ds3 11 }

   dsx3FarEndIntervalEntry OBJECT-TYPE
        SYNTAX  Dsx3FarEndIntervalEntry
        MAX-ACCESS  not-accessible
        STATUS  current
        INDEX   { dsx3FarEndIntervalIndex,
                  dsx3FarEndIntervalNumber }
        ::= { dsx3FarEndIntervalTable 1 }

   Dsx3FarEndIntervalEntry ::=
        SEQUENCE {
             dsx3FarEndIntervalIndex      InterfaceIndex,
             dsx3FarEndIntervalNumber     INTEGER,
             dsx3FarEndIntervalCESs       PerfIntervalCount,
             dsx3FarEndIntervalCSESs      PerfIntervalCount,
             dsx3FarEndIntervalCCVs       PerfIntervalCount,
             dsx3FarEndIntervalUASs       PerfIntervalCount,
             dsx3FarEndIntervalValidData  TruthValue
       }

   dsx3FarEndIntervalIndex OBJECT-TYPE
        SYNTAX  InterfaceIndex
        MAX-ACCESS  read-only  -- read-only since originally an
        STATUS  current
        ::= { dsx3FarEndIntervalEntry 1 }

   dsx3FarEndIntervalNumber OBJECT-TYPE
       SYNTAX  INTEGER (1..96)
       MAX-ACCESS  read-only  -- read-only since originally an
       STATUS  current
       ::= { dsx3FarEndIntervalEntry 2 }

   dsx3FarEndIntervalCESs OBJECT-TYPE
       SYNTAX  PerfIntervalCount
       MAX-ACCESS  read-only
       STATUS  current
       ::= { dsx3FarEndIntervalEntry 3 }

   dsx3FarEndIntervalCSESs OBJECT-TYPE
       SYNTAX  PerfIntervalCount
       MAX-ACCESS  read-only
       STATUS  current
        ::= { dsx3FarEndIntervalEntry 4 }

   dsx3FarEndIntervalCCVs OBJECT-TYPE
        SYNTAX  PerfIntervalCount
        MAX-ACCESS  read-only
        STATUS  current
        ::= { dsx3FarEndIntervalEntry 5 }

   dsx3FarEndIntervalUASs OBJECT-TYPE
        SYNTAX  PerfIntervalCount
        MAX-ACCESS  read-only
        STATUS  current
        ::= { dsx3FarEndIntervalEntry 6 }

   dsx3FarEndIntervalValidData OBJECT-TYPE
        SYNTAX  TruthValue
        MAX-ACCESS  read-only





        STATUS  current
        ::= { dsx3FarEndIntervalEntry 7 }


   dsx3FarEndTotalTable OBJECT-TYPE
        SYNTAX  SEQUENCE OF Dsx3FarEndTotalEntry
        MAX-ACCESS  not-accessible
        STATUS  current
        ::= { ds3 12 }

   dsx3FarEndTotalEntry OBJECT-TYPE
        SYNTAX  Dsx3FarEndTotalEntry
        MAX-ACCESS  not-accessible
        STATUS  current
        INDEX   { dsx3FarEndTotalIndex }
        ::= { dsx3FarEndTotalTable 1 }

   Dsx3FarEndTotalEntry ::=
        SEQUENCE {
            dsx3FarEndTotalIndex       InterfaceIndex,
            dsx3FarEndTotalCESs        PerfTotalCount,
            dsx3FarEndTotalCSESs       PerfTotalCount,
            dsx3FarEndTotalCCVs        PerfTotalCount,
            dsx3FarEndTotalUASs        PerfTotalCount
        }

   dsx3FarEndTotalIndex OBJECT-TYPE
       SYNTAX  InterfaceIndex
       MAX-ACCESS  read-only  -- read-only since originally an
       STATUS  current
       ::= { dsx3FarEndTotalEntry 1 }





   dsx3FarEndTotalCESs OBJECT-TYPE
       SYNTAX  PerfTotalCount
       MAX-ACCESS  read-only
       STATUS  current
       ::= { dsx3FarEndTotalEntry 2 }

   dsx3FarEndTotalCSESs OBJECT-TYPE
       SYNTAX  PerfTotalCount
       MAX-ACCESS  read-only
       STATUS  current
       ::= { dsx3FarEndTotalEntry 3 }

   dsx3FarEndTotalCCVs OBJECT-TYPE
       SYNTAX  PerfTotalCount
       MAX-ACCESS  read-only
       STATUS  current
       ::= { dsx3FarEndTotalEntry 4 }

   dsx3FarEndTotalUASs OBJECT-TYPE
       SYNTAX  PerfTotalCount
       MAX-ACCESS  read-only
       STATUS  current
       ::= { dsx3FarEndTotalEntry 5 }







   dsx3FracTable OBJECT-TYPE
       SYNTAX  SEQUENCE OF Dsx3FracEntry
       MAX-ACCESS  not-accessible
       STATUS  deprecated
        ::= { ds3 13 }






   dsx3FracEntry OBJECT-TYPE
        SYNTAX  Dsx3FracEntry
        MAX-ACCESS  not-accessible
        STATUS  deprecated
       INDEX   { dsx3FracIndex, dsx3FracNumber }
       ::= { dsx3FracTable 1 }

   Dsx3FracEntry ::=
        SEQUENCE {
            dsx3FracIndex     INTEGER,
            dsx3FracNumber    INTEGER,
            dsx3FracIfIndex   INTEGER
       }

   dsx3FracIndex OBJECT-TYPE
       SYNTAX  INTEGER (1..'7fffffff'h)
       MAX-ACCESS  read-only -- read-only since originally an
       STATUS  deprecated
       ::= { dsx3FracEntry 1 }

   dsx3FracNumber OBJECT-TYPE
       SYNTAX  INTEGER (1..31)
       MAX-ACCESS  read-only  -- read-only since originally an
       STATUS  deprecated
      ::= { dsx3FracEntry 2 }

   dsx3FracIfIndex OBJECT-TYPE
      SYNTAX  INTEGER (0..'7fffffff'h)
      MAX-ACCESS  read-write
      STATUS  deprecated
      ::= { dsx3FracEntry 3 }


   ds3Traps OBJECT IDENTIFIER ::= { ds3 15 }

   dsx3LineStatusChange NOTIFICATION-TYPE
       OBJECTS { dsx3LineStatus,
                 dsx3LineStatusLastChange }
       STATUS  current
        ::= { ds3Traps 0 1 }


   ds3Conformance OBJECT IDENTIFIER ::= { ds3 14 }
   ds3Groups      OBJECT IDENTIFIER ::= { ds3Conformance 1 }
   ds3Compliances OBJECT IDENTIFIER ::= { ds3Conformance 2 }


   ds3Compliance MODULE-COMPLIANCE
       STATUS  current
       MODULE  -- this module
           MANDATORY-GROUPS { ds3NearEndConfigGroup,
                              ds3NearEndStatisticsGroup }

           GROUP       ds3FarEndGroup
           GROUP       ds3NearEndOptionalTrapGroup





           GROUP       ds3NearEndOptionalConfigGroup

           OBJECT      dsx3LineType
           MIN-ACCESS  read-only

           OBJECT      dsx3LineCoding
           MIN-ACCESS  read-only

           OBJECT      dsx3SendCode
           MIN-ACCESS  read-only

           OBJECT      dsx3LoopbackConfig
           MIN-ACCESS  read-only

           OBJECT      dsx3TransmitClockSource
           MIN-ACCESS  read-only

           OBJECT      dsx3LineLength
           MIN-ACCESS  read-only

           OBJECT      dsx3Channelization
           MIN-ACCESS  read-only





       ::= { ds3Compliances 1 }


   ds3NearEndConfigGroup  OBJECT-GROUP
       OBJECTS { dsx3LineIndex,
                 dsx3TimeElapsed,
                 dsx3ValidIntervals,
                 dsx3LineType,
                 dsx3LineCoding,
                 dsx3SendCode,
                 dsx3CircuitIdentifier,
                 dsx3LoopbackConfig,
                 dsx3LineStatus,
                 dsx3TransmitClockSource,
                 dsx3InvalidIntervals,
                 dsx3LineLength,
                 dsx3LoopbackStatus,
                 dsx3Channelization,
                 dsx3Ds1ForRemoteLoop}
       STATUS  current
       ::= { ds3Groups 1 }

   ds3NearEndStatisticsGroup OBJECT-GROUP
       OBJECTS { dsx3CurrentIndex,
                 dsx3CurrentPESs,
                 dsx3CurrentPSESs,
                 dsx3CurrentSEFSs,
                 dsx3CurrentUASs,
                 dsx3CurrentLCVs,
                 dsx3CurrentPCVs,
                 dsx3CurrentLESs,
                 dsx3CurrentCCVs,
                 dsx3CurrentCESs,
                 dsx3CurrentCSESs,
                 dsx3IntervalIndex,
                 dsx3IntervalNumber,
                 dsx3IntervalPESs,
                 dsx3IntervalPSESs,
                 dsx3IntervalSEFSs,
                 dsx3IntervalUASs,
                 dsx3IntervalLCVs,
                 dsx3IntervalPCVs,
                 dsx3IntervalLESs,
                 dsx3IntervalCCVs,





                 dsx3IntervalCESs,
                 dsx3IntervalCSESs,
                 dsx3IntervalValidData,
                 dsx3TotalIndex,
                 dsx3TotalPESs,
                 dsx3TotalPSESs,
                 dsx3TotalSEFSs,
                 dsx3TotalUASs,
                 dsx3TotalLCVs,
                 dsx3TotalPCVs,
                 dsx3TotalLESs,
                 dsx3TotalCCVs,
                 dsx3TotalCESs,
                 dsx3TotalCSESs }
       STATUS  current
       ::= { ds3Groups 2 }

   ds3FarEndGroup  OBJECT-GROUP
       OBJECTS { dsx3FarEndLineIndex,
                 dsx3FarEndEquipCode,
                 dsx3FarEndLocationIDCode,
                 dsx3FarEndFrameIDCode,
                 dsx3FarEndUnitCode,
                 dsx3FarEndFacilityIDCode,
                 dsx3FarEndCurrentIndex,
                 dsx3FarEndTimeElapsed,
                 dsx3FarEndValidIntervals,
                 dsx3FarEndCurrentCESs,
                 dsx3FarEndCurrentCSESs,
                 dsx3FarEndCurrentCCVs,
                 dsx3FarEndCurrentUASs,
                 dsx3FarEndInvalidIntervals,
                 dsx3FarEndIntervalIndex,
                 dsx3FarEndIntervalNumber,
                 dsx3FarEndIntervalCESs,
                 dsx3FarEndIntervalCSESs,
                 dsx3FarEndIntervalCCVs,
                 dsx3FarEndIntervalUASs,
                 dsx3FarEndIntervalValidData,
                 dsx3FarEndTotalIndex,
                 dsx3FarEndTotalCESs,
                 dsx3FarEndTotalCSESs,
                 dsx3FarEndTotalCCVs,
                 dsx3FarEndTotalUASs }
       STATUS  current





       ::= { ds3Groups 3 }

   ds3DeprecatedGroup OBJECT-GROUP

       OBJECTS { dsx3IfIndex,
                 dsx3FracIndex,
                 dsx3FracNumber,
                 dsx3FracIfIndex }
       STATUS  deprecated
       ::= { ds3Groups 4 }

   ds3NearEndOptionalConfigGroup OBJECT-GROUP
       OBJECTS { dsx3LineStatusLastChange,
                 dsx3LineStatusChangeTrapEnable }

       STATUS    current
       ::= { ds3Groups 5 }

   ds3NearEndOptionalTrapGroup NOTIFICATION-GROUP
       NOTIFICATIONS { dsx3LineStatusChange }
       STATUS    current
       ::= { ds3Groups 6 }

   END

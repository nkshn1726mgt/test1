DNS-RESOLVER-MIB DEFINITIONS ::= BEGIN

   IMPORTS
       MODULE-IDENTITY, OBJECT-TYPE, IpAddress, Counter32, Integer32
           FROM SNMPv2-SMI
       TEXTUAL-CONVENTION, RowStatus, DisplayString
           FROM SNMPv2-TC
       MODULE-COMPLIANCE, OBJECT-GROUP
           FROM SNMPv2-CONF
       dns, DnsName, DnsNameAsIndex, DnsClass, DnsType, DnsQClass,
       DnsQType, DnsTime, DnsOpCode, DnsRespCode
           FROM DNS-SERVER-MIB;


   dnsResMIB MODULE-IDENTITY
       LAST-UPDATED "9401282250Z"
       ORGANIZATION "IETF DNS Working Group"





       ::= { dns 2 }

   dnsResMIBObjects        OBJECT IDENTIFIER ::= { dnsResMIB 1 }


   dnsResConfig            OBJECT IDENTIFIER ::= { dnsResMIBObjects 1 }
   dnsResCounter           OBJECT IDENTIFIER ::= { dnsResMIBObjects 2 }
   dnsResLameDelegation    OBJECT IDENTIFIER ::= { dnsResMIBObjects 3 }
   dnsResCache             OBJECT IDENTIFIER ::= { dnsResMIBObjects 4 }
   dnsResNCache            OBJECT IDENTIFIER ::= { dnsResMIBObjects 5 }
   dnsResOptCounter        OBJECT IDENTIFIER ::= { dnsResMIBObjects 6 }



   dnsResConfigImplementIdent OBJECT-TYPE
       SYNTAX      DisplayString
       MAX-ACCESS  read-only
       STATUS      current
       ::= { dnsResConfig 1 }

   dnsResConfigService OBJECT-TYPE
       SYNTAX      INTEGER { recursiveOnly(1),
                             iterativeOnly(2),
                             recursiveAndIterative(3) }
       MAX-ACCESS  read-only
       STATUS      current
        ::= { dnsResConfig 2 }

   dnsResConfigMaxCnames OBJECT-TYPE
       SYNTAX      INTEGER (0..2147483647)
       MAX-ACCESS  read-write





       STATUS      current
       ::= { dnsResConfig 3 }


   dnsResConfigSbeltTable OBJECT-TYPE
       SYNTAX      SEQUENCE OF DnsResConfigSbeltEntry
       MAX-ACCESS  not-accessible
       STATUS      current
       ::= { dnsResConfig 4 }

   dnsResConfigSbeltEntry OBJECT-TYPE
       SYNTAX      DnsResConfigSbeltEntry
       MAX-ACCESS  not-accessible
       STATUS      current
       INDEX     { dnsResConfigSbeltAddr,
                   dnsResConfigSbeltSubTree,
                   dnsResConfigSbeltClass }
       ::= { dnsResConfigSbeltTable 1 }

   DnsResConfigSbeltEntry ::=
       SEQUENCE {
           dnsResConfigSbeltAddr
               IpAddress,
           dnsResConfigSbeltName
               DnsName,
           dnsResConfigSbeltRecursion
               INTEGER,
           dnsResConfigSbeltPref
               INTEGER,
           dnsResConfigSbeltSubTree





               DnsNameAsIndex,
           dnsResConfigSbeltClass
               DnsClass,
           dnsResConfigSbeltStatus
               RowStatus
       }

   dnsResConfigSbeltAddr OBJECT-TYPE
       SYNTAX      IpAddress
       MAX-ACCESS  not-accessible
       STATUS      current
       ::= { dnsResConfigSbeltEntry 1 }

   dnsResConfigSbeltName OBJECT-TYPE
       SYNTAX      DnsName
       MAX-ACCESS  read-create
       STATUS      current
       ::= { dnsResConfigSbeltEntry 2 }

   dnsResConfigSbeltRecursion OBJECT-TYPE
       SYNTAX      INTEGER { iterative(1),
                             recursive(2),
                             recursiveAndIterative(3) }
       MAX-ACCESS  read-create
       STATUS      current
        ::= { dnsResConfigSbeltEntry 3 }





   dnsResConfigSbeltPref OBJECT-TYPE
       SYNTAX      INTEGER (0..2147483647)
       MAX-ACCESS  read-create
       STATUS      current
        ::= { dnsResConfigSbeltEntry 4 }

   dnsResConfigSbeltSubTree OBJECT-TYPE
       SYNTAX      DnsNameAsIndex
       MAX-ACCESS  not-accessible
       STATUS      current
       ::= { dnsResConfigSbeltEntry 5 }

   dnsResConfigSbeltClass OBJECT-TYPE
       SYNTAX      DnsClass
       MAX-ACCESS  not-accessible
       STATUS      current
       ::= { dnsResConfigSbeltEntry 6 }

   dnsResConfigSbeltStatus OBJECT-TYPE
       SYNTAX      RowStatus
       MAX-ACCESS  read-create
       STATUS      current
       ::= { dnsResConfigSbeltEntry 7 }

   dnsResConfigUpTime OBJECT-TYPE
       SYNTAX      DnsTime
       MAX-ACCESS  read-only
       STATUS      current
       ::= { dnsResConfig 5 }

   dnsResConfigResetTime OBJECT-TYPE
       SYNTAX      DnsTime
       MAX-ACCESS  read-only
       STATUS      current
       ::= { dnsResConfig 6 }

   dnsResConfigReset OBJECT-TYPE
       SYNTAX      INTEGER { other(1),
                             reset(2),
                             initializing(3),
                             running(4) }
       MAX-ACCESS  read-write
       STATUS      current
       ::= { dnsResConfig 7 }




   dnsResCounterByOpcodeTable OBJECT-TYPE
       SYNTAX      SEQUENCE OF DnsResCounterByOpcodeEntry
       MAX-ACCESS  not-accessible
       STATUS      current
       ::= { dnsResCounter 3 }

   dnsResCounterByOpcodeEntry OBJECT-TYPE
       SYNTAX      DnsResCounterByOpcodeEntry
       MAX-ACCESS  not-accessible
       STATUS      current
       INDEX     { dnsResCounterByOpcodeCode }
       ::= { dnsResCounterByOpcodeTable 1 }

   DnsResCounterByOpcodeEntry ::=
       SEQUENCE {
           dnsResCounterByOpcodeCode
               DnsOpCode,
           dnsResCounterByOpcodeQueries
               Counter32,
           dnsResCounterByOpcodeResponses
               Counter32
       }

   dnsResCounterByOpcodeCode OBJECT-TYPE
       SYNTAX      DnsOpCode
       MAX-ACCESS  not-accessible
       STATUS      current
       ::= { dnsResCounterByOpcodeEntry 1 }

   dnsResCounterByOpcodeQueries OBJECT-TYPE
       SYNTAX      Counter32
       MAX-ACCESS  read-only
       STATUS      current
       ::= { dnsResCounterByOpcodeEntry 2 }

   dnsResCounterByOpcodeResponses OBJECT-TYPE
       SYNTAX      Counter32
       MAX-ACCESS  read-only
       STATUS      current





       ::= { dnsResCounterByOpcodeEntry 3 }


   dnsResCounterByRcodeTable OBJECT-TYPE
       SYNTAX      SEQUENCE OF DnsResCounterByRcodeEntry
       MAX-ACCESS  not-accessible
       STATUS      current
       ::= { dnsResCounter 4 }

   dnsResCounterByRcodeEntry OBJECT-TYPE
       SYNTAX      DnsResCounterByRcodeEntry
       MAX-ACCESS  not-accessible
       STATUS      current
       INDEX     { dnsResCounterByRcodeCode }
       ::= { dnsResCounterByRcodeTable 1 }

   DnsResCounterByRcodeEntry ::=
       SEQUENCE {
           dnsResCounterByRcodeCode
               DnsRespCode,
           dnsResCounterByRcodeResponses
               Counter32
       }

   dnsResCounterByRcodeCode OBJECT-TYPE
       SYNTAX      DnsRespCode
       MAX-ACCESS  not-accessible
       STATUS      current
       ::= { dnsResCounterByRcodeEntry 1 }








   dnsResCounterByRcodeResponses OBJECT-TYPE
       SYNTAX      Counter32
       MAX-ACCESS  read-only
       STATUS      current
       ::= { dnsResCounterByRcodeEntry 2 }


   dnsResCounterNonAuthDataResps OBJECT-TYPE
       SYNTAX      Counter32
       MAX-ACCESS  read-only
       STATUS      current
       ::= { dnsResCounter 5 }

   dnsResCounterNonAuthNoDataResps OBJECT-TYPE
       SYNTAX      Counter32
       MAX-ACCESS  read-only
       STATUS      current
       ::= { dnsResCounter 6 }

   dnsResCounterMartians OBJECT-TYPE
       SYNTAX      Counter32
       MAX-ACCESS  read-only
       STATUS      current
       ::= { dnsResCounter 7 }

   dnsResCounterRecdResponses OBJECT-TYPE
       SYNTAX      Counter32
       MAX-ACCESS  read-only
       STATUS      current
       ::= { dnsResCounter 8 }






   dnsResCounterUnparseResps OBJECT-TYPE
       SYNTAX      Counter32
       MAX-ACCESS  read-only
       STATUS      current
       ::= { dnsResCounter 9 }

   dnsResCounterFallbacks OBJECT-TYPE
       SYNTAX      Counter32
       MAX-ACCESS  read-only
       STATUS      current
       ::= { dnsResCounter 10 }



   dnsResLameDelegationOverflows OBJECT-TYPE
       SYNTAX      Counter32
       MAX-ACCESS  read-only
       STATUS      current
       ::= { dnsResLameDelegation 1 }


   dnsResLameDelegationTable OBJECT-TYPE
       SYNTAX      SEQUENCE OF DnsResLameDelegationEntry
       MAX-ACCESS  not-accessible
       STATUS      current
       ::= { dnsResLameDelegation 2 }

   dnsResLameDelegationEntry OBJECT-TYPE
       SYNTAX      DnsResLameDelegationEntry
       MAX-ACCESS  not-accessible





       STATUS      current
       INDEX     { dnsResLameDelegationSource,
                   dnsResLameDelegationName,
                   dnsResLameDelegationClass }
       ::= { dnsResLameDelegationTable 1 }

   DnsResLameDelegationEntry ::=
       SEQUENCE {
           dnsResLameDelegationSource
               IpAddress,
           dnsResLameDelegationName
               DnsNameAsIndex,
           dnsResLameDelegationClass
               DnsClass,
           dnsResLameDelegationCounts
               Counter32,
           dnsResLameDelegationStatus
               RowStatus
       }

   dnsResLameDelegationSource OBJECT-TYPE
       SYNTAX      IpAddress
       MAX-ACCESS  not-accessible
       STATUS      current
       ::= { dnsResLameDelegationEntry 1 }

   dnsResLameDelegationName OBJECT-TYPE
       SYNTAX      DnsNameAsIndex
       MAX-ACCESS  not-accessible
       STATUS      current
       ::= { dnsResLameDelegationEntry 2 }

   dnsResLameDelegationClass OBJECT-TYPE
       SYNTAX      DnsClass
       MAX-ACCESS  not-accessible
       STATUS      current
       ::= { dnsResLameDelegationEntry 3 }






   dnsResLameDelegationCounts OBJECT-TYPE
       SYNTAX      Counter32
       MAX-ACCESS  read-only
       STATUS      current
       ::= { dnsResLameDelegationEntry 4 }

   dnsResLameDelegationStatus OBJECT-TYPE
       SYNTAX      RowStatus
       MAX-ACCESS  read-write
       STATUS      current
       ::= { dnsResLameDelegationEntry 5 }



   dnsResCacheStatus OBJECT-TYPE
       SYNTAX      INTEGER { enabled(1), disabled(2), clear(3) }
       MAX-ACCESS  read-write
       STATUS      current
       ::= { dnsResCache 1 }

   dnsResCacheMaxTTL OBJECT-TYPE
       SYNTAX      DnsTime
       MAX-ACCESS  read-write
       STATUS      current
       ::= { dnsResCache 2 }

   dnsResCacheGoodCaches OBJECT-TYPE
       SYNTAX      Counter32
       MAX-ACCESS  read-only
       STATUS      current
       ::= { dnsResCache 3 }

   dnsResCacheBadCaches OBJECT-TYPE
       SYNTAX      Counter32
       MAX-ACCESS  read-only
       STATUS      current
       ::= { dnsResCache 4 }


   dnsResCacheRRTable OBJECT-TYPE
       SYNTAX      SEQUENCE OF DnsResCacheRREntry
       MAX-ACCESS  not-accessible
       STATUS      current
       ::= { dnsResCache 5 }

   dnsResCacheRREntry OBJECT-TYPE
       SYNTAX      DnsResCacheRREntry
       MAX-ACCESS  not-accessible
       STATUS      current
       INDEX     { dnsResCacheRRName,
                   dnsResCacheRRClass,
                   dnsResCacheRRType,
                   dnsResCacheRRIndex }





       ::= { dnsResCacheRRTable 1 }

   DnsResCacheRREntry ::=
       SEQUENCE {
           dnsResCacheRRName
               DnsNameAsIndex,
           dnsResCacheRRClass
               DnsClass,
           dnsResCacheRRType
               DnsType,
           dnsResCacheRRTTL
               DnsTime,
           dnsResCacheRRElapsedTTL
               DnsTime,
           dnsResCacheRRSource
               IpAddress,
           dnsResCacheRRData
               OCTET STRING,
           dnsResCacheRRStatus
               RowStatus,
           dnsResCacheRRIndex
               Integer32,
           dnsResCacheRRPrettyName
               DnsName
       }

   dnsResCacheRRName OBJECT-TYPE
       SYNTAX      DnsNameAsIndex
       MAX-ACCESS  not-accessible
       STATUS      current
       ::= { dnsResCacheRREntry 1 }

   dnsResCacheRRClass OBJECT-TYPE
       SYNTAX      DnsClass
       MAX-ACCESS  not-accessible
       STATUS      current
       ::= { dnsResCacheRREntry 2 }






   dnsResCacheRRType OBJECT-TYPE
       SYNTAX      DnsType
       MAX-ACCESS  not-accessible
       STATUS      current
       ::= { dnsResCacheRREntry 3 }

   dnsResCacheRRTTL OBJECT-TYPE
       SYNTAX      DnsTime
       MAX-ACCESS  read-only
       STATUS      current
       ::= { dnsResCacheRREntry 4 }

   dnsResCacheRRElapsedTTL OBJECT-TYPE
       SYNTAX      DnsTime
       MAX-ACCESS  read-only
       STATUS      current
       ::= { dnsResCacheRREntry 5 }

   dnsResCacheRRSource OBJECT-TYPE
       SYNTAX      IpAddress
       MAX-ACCESS  read-only
       STATUS      current
       ::= { dnsResCacheRREntry 6 }

   dnsResCacheRRData OBJECT-TYPE
       SYNTAX      OCTET STRING
       MAX-ACCESS  read-only
       STATUS      current
       ::= { dnsResCacheRREntry 7 }







   dnsResCacheRRStatus OBJECT-TYPE
       SYNTAX      RowStatus
       MAX-ACCESS  read-write
       STATUS      current
       ::= { dnsResCacheRREntry 8 }

   dnsResCacheRRIndex OBJECT-TYPE
       SYNTAX      Integer32
       MAX-ACCESS  not-accessible
       STATUS      current
       ::= { dnsResCacheRREntry 9 }

   dnsResCacheRRPrettyName OBJECT-TYPE
       SYNTAX      DnsName
       MAX-ACCESS  read-only
       STATUS      current
       ::= { dnsResCacheRREntry 10 }


   dnsResNCacheStatus OBJECT-TYPE
       SYNTAX      INTEGER { enabled(1), disabled(2), clear(3) }
       MAX-ACCESS  read-write
       STATUS      current
       ::= { dnsResNCache 1 }

   dnsResNCacheMaxTTL OBJECT-TYPE
       SYNTAX      DnsTime
       MAX-ACCESS  read-write
       STATUS      current
       ::= { dnsResNCache 2 }

   dnsResNCacheGoodNCaches OBJECT-TYPE
       SYNTAX      Counter32
       MAX-ACCESS  read-only
       STATUS      current
       ::= { dnsResNCache 3 }

   dnsResNCacheBadNCaches OBJECT-TYPE
       SYNTAX      Counter32
       MAX-ACCESS  read-only
       STATUS      current
       ::= { dnsResNCache 4 }


   dnsResNCacheErrTable OBJECT-TYPE
       SYNTAX      SEQUENCE OF DnsResNCacheErrEntry
       MAX-ACCESS  not-accessible
       STATUS      current





       ::= { dnsResNCache 5 }

   dnsResNCacheErrEntry OBJECT-TYPE
       SYNTAX      DnsResNCacheErrEntry
       MAX-ACCESS  not-accessible
       STATUS      current
       INDEX     { dnsResNCacheErrQName,
                   dnsResNCacheErrQClass,
                   dnsResNCacheErrQType,
                   dnsResNCacheErrIndex }
       ::= { dnsResNCacheErrTable 1 }

   DnsResNCacheErrEntry ::=
       SEQUENCE {
           dnsResNCacheErrQName
               DnsNameAsIndex,
           dnsResNCacheErrQClass
               DnsQClass,
           dnsResNCacheErrQType
               DnsQType,
           dnsResNCacheErrTTL
               DnsTime,
           dnsResNCacheErrElapsedTTL
               DnsTime,
           dnsResNCacheErrSource
               IpAddress,
           dnsResNCacheErrCode
               INTEGER,
           dnsResNCacheErrStatus
               RowStatus,
           dnsResNCacheErrIndex
               Integer32,
           dnsResNCacheErrPrettyName
               DnsName
       }

   dnsResNCacheErrQName OBJECT-TYPE
       SYNTAX      DnsNameAsIndex
       MAX-ACCESS  not-accessible
       STATUS      current





       ::= { dnsResNCacheErrEntry 1 }

   dnsResNCacheErrQClass OBJECT-TYPE
       SYNTAX      DnsQClass
       MAX-ACCESS  not-accessible
       STATUS      current
       ::= { dnsResNCacheErrEntry 2 }

   dnsResNCacheErrQType OBJECT-TYPE
       SYNTAX      DnsQType
       MAX-ACCESS  not-accessible
       STATUS      current
       ::= { dnsResNCacheErrEntry 3 }

   dnsResNCacheErrTTL OBJECT-TYPE
       SYNTAX      DnsTime
       MAX-ACCESS  read-only
       STATUS      current
       ::= { dnsResNCacheErrEntry 4 }

   dnsResNCacheErrElapsedTTL OBJECT-TYPE
       SYNTAX      DnsTime
       MAX-ACCESS  read-only
       STATUS      current
       ::= { dnsResNCacheErrEntry 5 }







   dnsResNCacheErrSource OBJECT-TYPE
       SYNTAX      IpAddress
       MAX-ACCESS  read-only
       STATUS      current
       ::= { dnsResNCacheErrEntry 6 }

   dnsResNCacheErrCode OBJECT-TYPE
       SYNTAX      INTEGER { nonexistantName(1), noData(2), other(3) }
       MAX-ACCESS  read-only
       STATUS      current
       ::= { dnsResNCacheErrEntry 7 }

   dnsResNCacheErrStatus OBJECT-TYPE
       SYNTAX      RowStatus
       MAX-ACCESS  read-write
       STATUS      current
       ::= { dnsResNCacheErrEntry 8 }

   dnsResNCacheErrIndex OBJECT-TYPE
       SYNTAX      Integer32
       MAX-ACCESS  read-only
       STATUS      current
       ::= { dnsResNCacheErrEntry 9 }






   dnsResNCacheErrPrettyName OBJECT-TYPE
       SYNTAX      DnsName
       MAX-ACCESS  read-only
       STATUS      current
       ::= { dnsResNCacheErrEntry 10 }



   dnsResOptCounterReferals OBJECT-TYPE
       SYNTAX      Counter32
       MAX-ACCESS  read-only
       STATUS      current
       ::= { dnsResOptCounter 1 }

   dnsResOptCounterRetrans OBJECT-TYPE
       SYNTAX      Counter32
       MAX-ACCESS  read-only
       STATUS      current
       ::= { dnsResOptCounter 2 }

   dnsResOptCounterNoResponses OBJECT-TYPE
       SYNTAX      Counter32
       MAX-ACCESS  read-only
       STATUS      current
       ::= { dnsResOptCounter 3 }

   dnsResOptCounterRootRetrans OBJECT-TYPE
       SYNTAX      Counter32
       MAX-ACCESS  read-only
       STATUS      current
       ::= { dnsResOptCounter 4 }

   dnsResOptCounterInternals OBJECT-TYPE
       SYNTAX      Counter32
       MAX-ACCESS  read-only
       STATUS      current
       ::= { dnsResOptCounter 5 }

   dnsResOptCounterInternalTimeOuts OBJECT-TYPE
       SYNTAX      Counter32
       MAX-ACCESS  read-only
       STATUS      current
       ::= { dnsResOptCounter 6 }



   dnsResMIBGroups         OBJECT IDENTIFIER ::= { dnsResMIB 2 }

   dnsResConfigGroup OBJECT-GROUP
       OBJECTS   { dnsResConfigImplementIdent,
                   dnsResConfigService,
                   dnsResConfigMaxCnames,
                   dnsResConfigSbeltAddr,
                   dnsResConfigSbeltName,
                   dnsResConfigSbeltRecursion,
                   dnsResConfigSbeltPref,
                   dnsResConfigSbeltSubTree,
                   dnsResConfigSbeltClass,
                   dnsResConfigSbeltStatus,
                   dnsResConfigUpTime,
                   dnsResConfigResetTime }
       STATUS      current
       ::= { dnsResMIBGroups 1 }

   dnsResCounterGroup OBJECT-GROUP
       OBJECTS   { dnsResCounterByOpcodeCode,
                   dnsResCounterByOpcodeQueries,





                   dnsResCounterByOpcodeResponses,
                   dnsResCounterByRcodeCode,
                   dnsResCounterByRcodeResponses,
                   dnsResCounterNonAuthDataResps,
                   dnsResCounterNonAuthNoDataResps,
                   dnsResCounterMartians,
                   dnsResCounterRecdResponses,
                   dnsResCounterUnparseResps,
                   dnsResCounterFallbacks }
       STATUS      current
       ::= { dnsResMIBGroups 2 }

   dnsResLameDelegationGroup OBJECT-GROUP
       OBJECTS   { dnsResLameDelegationOverflows,
                   dnsResLameDelegationSource,
                   dnsResLameDelegationName,
                   dnsResLameDelegationClass,
                   dnsResLameDelegationCounts,
                   dnsResLameDelegationStatus }
       STATUS      current
       ::= { dnsResMIBGroups 3 }


   dnsResCacheGroup OBJECT-GROUP
       OBJECTS   { dnsResCacheStatus,
                   dnsResCacheMaxTTL,
                   dnsResCacheGoodCaches,
                   dnsResCacheBadCaches,
                   dnsResCacheRRName,
                   dnsResCacheRRClass,
                   dnsResCacheRRType,
                   dnsResCacheRRTTL,
                   dnsResCacheRRElapsedTTL,
                   dnsResCacheRRSource,
                   dnsResCacheRRData,
                   dnsResCacheRRStatus,
                   dnsResCacheRRIndex,
                   dnsResCacheRRPrettyName }
       STATUS      current





       ::= { dnsResMIBGroups 4 }

   dnsResNCacheGroup OBJECT-GROUP
       OBJECTS   { dnsResNCacheStatus,
                   dnsResNCacheMaxTTL,
                   dnsResNCacheGoodNCaches,
                   dnsResNCacheBadNCaches,
                   dnsResNCacheErrQName,
                   dnsResNCacheErrQClass,
                   dnsResNCacheErrQType,
                   dnsResNCacheErrTTL,
                   dnsResNCacheErrElapsedTTL,
                   dnsResNCacheErrSource,
                   dnsResNCacheErrCode,
                   dnsResNCacheErrStatus,
                   dnsResNCacheErrIndex,
                   dnsResNCacheErrPrettyName }
       STATUS      current
       ::= { dnsResMIBGroups 5 }

   dnsResOptCounterGroup OBJECT-GROUP
       OBJECTS   { dnsResOptCounterReferals,
                   dnsResOptCounterRetrans,
                   dnsResOptCounterNoResponses,
                   dnsResOptCounterRootRetrans,
                   dnsResOptCounterInternals,
                   dnsResOptCounterInternalTimeOuts }
       STATUS      current
       ::= { dnsResMIBGroups 6 }



   dnsResMIBCompliances OBJECT IDENTIFIER ::= { dnsResMIB 3 }

   dnsResMIBCompliance MODULE-COMPLIANCE
       STATUS      current
       MODULE -- This MIB module





           MANDATORY-GROUPS { dnsResConfigGroup, dnsResCounterGroup }
           GROUP   dnsResCacheGroup
           GROUP   dnsResNCacheGroup
           GROUP   dnsResLameDelegationGroup
           GROUP   dnsResOptCounterGroup
           OBJECT  dnsResConfigMaxCnames
           MIN-ACCESS      read-only
           OBJECT  dnsResConfigSbeltName
           MIN-ACCESS      read-only
           OBJECT  dnsResConfigSbeltRecursion
           MIN-ACCESS      read-only
           OBJECT  dnsResConfigSbeltPref
           MIN-ACCESS      read-only
           OBJECT  dnsResConfigReset
           MIN-ACCESS      read-only
           OBJECT  dnsResCacheStatus
           MIN-ACCESS      read-only
           OBJECT  dnsResCacheMaxTTL
           MIN-ACCESS      read-only
           OBJECT  dnsResNCacheStatus
           MIN-ACCESS      read-only





           OBJECT  dnsResNCacheMaxTTL
           MIN-ACCESS      read-only
       ::= { dnsResMIBCompliances 1 }

   END

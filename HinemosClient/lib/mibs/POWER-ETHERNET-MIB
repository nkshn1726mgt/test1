POWER-ETHERNET-MIB DEFINITIONS ::= BEGIN

IMPORTS
           MODULE-IDENTITY, mib-2, OBJECT-TYPE, Integer32,
           Gauge32, Counter32, NOTIFICATION-TYPE
                   FROM SNMPv2-SMI
           TruthValue
                   FROM SNMPv2-TC
           MODULE-COMPLIANCE, OBJECT-GROUP, NOTIFICATION-GROUP
                   FROM SNMPv2-CONF

            SnmpAdminString
                    FROM SNMP-FRAMEWORK-MIB;

    powerEthernetMIB MODULE-IDENTITY

         LAST-UPDATED    "200311240000Z"  -- November 24, 2003
         ORGANIZATION "IETF Ethernet Interfaces and Hub MIB
                       Working Group"















       ::= { mib-2 105 }

pethNotifications OBJECT IDENTIFIER ::= { powerEthernetMIB 0 }
pethObjects       OBJECT IDENTIFIER ::= { powerEthernetMIB 1 }
pethConformance   OBJECT IDENTIFIER ::= { powerEthernetMIB 2 }


  pethPsePortTable OBJECT-TYPE
       SYNTAX      SEQUENCE OF PethPsePortEntry
       MAX-ACCESS  not-accessible
       STATUS      current
       ::= { pethObjects 1 }

   pethPsePortEntry OBJECT-TYPE
       SYNTAX      PethPsePortEntry
       MAX-ACCESS  not-accessible
       STATUS      current
       INDEX    { pethPsePortGroupIndex , pethPsePortIndex  }
       ::= { pethPsePortTable 1 }

   PethPsePortEntry ::= SEQUENCE {
       pethPsePortGroupIndex
          Integer32,
       pethPsePortIndex
          Integer32,
       pethPsePortAdminEnable
          TruthValue,
       pethPsePortPowerPairsControlAbility
          TruthValue,
       pethPsePortPowerPairs
          INTEGER,
       pethPsePortDetectionStatus
          INTEGER,
       pethPsePortPowerPriority
          INTEGER,





       pethPsePortMPSAbsentCounter
          Counter32,
       pethPsePortType
          SnmpAdminString,
       pethPsePortPowerClassifications
          INTEGER,
       pethPsePortInvalidSignatureCounter
          Counter32,
       pethPsePortPowerDeniedCounter
          Counter32,
       pethPsePortOverLoadCounter
          Counter32,
       pethPsePortShortCounter
          Counter32
  }

     pethPsePortGroupIndex OBJECT-TYPE
       SYNTAX      Integer32 (1..2147483647)
       MAX-ACCESS  not-accessible
       STATUS      current
       ::= { pethPsePortEntry 1 }

     pethPsePortIndex OBJECT-TYPE
       SYNTAX      Integer32 (1..2147483647)
       MAX-ACCESS  not-accessible
       STATUS      current
       ::= { pethPsePortEntry 2 }

     pethPsePortAdminEnable OBJECT-TYPE
    SYNTAX TruthValue
    MAX-ACCESS read-write
    STATUS current





    ::= { pethPsePortEntry 3 }

     pethPsePortPowerPairsControlAbility OBJECT-TYPE
    SYNTAX TruthValue
    MAX-ACCESS read-only
    STATUS current
    ::= { pethPsePortEntry 4 }

    pethPsePortPowerPairs OBJECT-TYPE
    SYNTAX INTEGER   {
               signal(1),
               spare(2)
     }
    MAX-ACCESS read-write
    STATUS current
    ::= { pethPsePortEntry 5 }

     pethPsePortDetectionStatus OBJECT-TYPE
    SYNTAX INTEGER   {
             disabled(1),
             searching(2),
               deliveringPower(3),
               fault(4),
               test(5),
               otherFault(6)
     }





    MAX-ACCESS read-only
    STATUS current
    ::= { pethPsePortEntry 6 }

     pethPsePortPowerPriority OBJECT-TYPE
    SYNTAX INTEGER   {
               critical(1),
               high(2),
               low(3)
     }
    MAX-ACCESS read-write
    STATUS current
    ::= { pethPsePortEntry 7 }

   pethPsePortMPSAbsentCounter OBJECT-TYPE
    SYNTAX Counter32
    MAX-ACCESS read-only
    STATUS current
    ::= { pethPsePortEntry 8 }

   pethPsePortType OBJECT-TYPE
    SYNTAX SnmpAdminString
    MAX-ACCESS read-write
    STATUS current
    ::= { pethPsePortEntry 9 }

    pethPsePortPowerClassifications OBJECT-TYPE
     SYNTAX INTEGER   {
               class0(1),
               class1(2),
               class2(3),
               class3(4),
               class4(5)
     }
    MAX-ACCESS read-only
    STATUS current
   ::= { pethPsePortEntry 10 }

   pethPsePortInvalidSignatureCounter OBJECT-TYPE
    SYNTAX Counter32
    MAX-ACCESS read-only
    STATUS current





    ::= { pethPsePortEntry 11 }

   pethPsePortPowerDeniedCounter OBJECT-TYPE
    SYNTAX Counter32
    MAX-ACCESS read-only
    STATUS current
    ::= { pethPsePortEntry 12 }

   pethPsePortOverLoadCounter OBJECT-TYPE
    SYNTAX Counter32
    MAX-ACCESS read-only
    STATUS current
    ::= { pethPsePortEntry 13 }

   pethPsePortShortCounter OBJECT-TYPE
    SYNTAX Counter32
    MAX-ACCESS read-only
    STATUS current
    ::= { pethPsePortEntry 14 }


pethMainPseObjects       OBJECT IDENTIFIER ::= { pethObjects 3 }






pethMainPseTable OBJECT-TYPE
       SYNTAX      SEQUENCE OF PethMainPseEntry
       MAX-ACCESS  not-accessible
       STATUS      current
       ::= { pethMainPseObjects 1 }

   pethMainPseEntry OBJECT-TYPE
       SYNTAX      PethMainPseEntry
       MAX-ACCESS  not-accessible
       STATUS      current
       INDEX    { pethMainPseGroupIndex }
       ::= { pethMainPseTable 1 }

   PethMainPseEntry ::= SEQUENCE {
       pethMainPseGroupIndex
           Integer32,
       pethMainPsePower
           Gauge32 ,
       pethMainPseOperStatus
           INTEGER,
       pethMainPseConsumptionPower
           Gauge32,
       pethMainPseUsageThreshold
           Integer32
   }
     pethMainPseGroupIndex OBJECT-TYPE
       SYNTAX       Integer32 (1..2147483647)
       MAX-ACCESS  not-accessible
       STATUS      current
       ::= { pethMainPseEntry 1 }





     pethMainPsePower OBJECT-TYPE
       SYNTAX      Gauge32  (1..65535)
       UNITS      "Watts"
       MAX-ACCESS  read-only
       STATUS      current
       ::= { pethMainPseEntry 2 }

     pethMainPseOperStatus OBJECT-TYPE
       SYNTAX INTEGER   {
               on(1),
               off(2),
               faulty(3)
          }
       MAX-ACCESS  read-only
       STATUS      current
       ::= { pethMainPseEntry 3 }

     pethMainPseConsumptionPower OBJECT-TYPE
       SYNTAX      Gauge32
       UNITS      "Watts"
       MAX-ACCESS  read-only
       STATUS      current
       ::= { pethMainPseEntry 4 }

     pethMainPseUsageThreshold OBJECT-TYPE
       SYNTAX      Integer32  (1..99)
       UNITS      "%"
       MAX-ACCESS  read-write
       STATUS      current
       ::= { pethMainPseEntry 5 }


pethNotificationControl        OBJECT IDENTIFIER ::= { pethObjects 4 }

pethNotificationControlTable OBJECT-TYPE
       SYNTAX      SEQUENCE OF PethNotificationControlEntry
       MAX-ACCESS  not-accessible





       STATUS      current
       ::= { pethNotificationControl 1 }

   pethNotificationControlEntry OBJECT-TYPE
       SYNTAX      PethNotificationControlEntry
       MAX-ACCESS  not-accessible
       STATUS      current
       INDEX    { pethNotificationControlGroupIndex }
       ::= { pethNotificationControlTable 1 }

   PethNotificationControlEntry ::= SEQUENCE {
       pethNotificationControlGroupIndex
           Integer32,
       pethNotificationControlEnable
           TruthValue
   }
     pethNotificationControlGroupIndex OBJECT-TYPE
       SYNTAX      Integer32 (1..2147483647)
       MAX-ACCESS  not-accessible
       STATUS      current
       ::= { pethNotificationControlEntry 1 }

      pethNotificationControlEnable  OBJECT-TYPE
       SYNTAX             TruthValue
       MAX-ACCESS         read-write
       STATUS             current
       ::= { pethNotificationControlEntry 2 }







     pethPsePortOnOffNotification NOTIFICATION-TYPE
         OBJECTS     { pethPsePortDetectionStatus }
         STATUS      current
          ::= { pethNotifications 1 }

     pethMainPowerUsageOnNotification NOTIFICATION-TYPE
         OBJECTS     { pethMainPseConsumptionPower  }
         STATUS      current
         ::= { pethNotifications 2 }

      pethMainPowerUsageOffNotification NOTIFICATION-TYPE
         OBJECTS     { pethMainPseConsumptionPower }
         STATUS      current
         ::= { pethNotifications 3 }

pethCompliances OBJECT IDENTIFIER ::= { pethConformance 1 }
pethGroups      OBJECT IDENTIFIER ::= { pethConformance 2 }

pethCompliance MODULE-COMPLIANCE
       STATUS  current





       MODULE  -- this module
           MANDATORY-GROUPS { pethPsePortGroup,
                              pethPsePortNotificationGroup,
                              pethNotificationControlGroup
                            }
           GROUP   pethMainPseGroup
           GROUP   pethMainPowerNotificationGroup
       ::= { pethCompliances 1 }

pethPsePortGroup OBJECT-GROUP
    OBJECTS {
       pethPsePortAdminEnable,
       pethPsePortPowerPairsControlAbility,
       pethPsePortPowerPairs,
       pethPsePortDetectionStatus,
       pethPsePortPowerPriority,
       pethPsePortMPSAbsentCounter,
       pethPsePortInvalidSignatureCounter,
       pethPsePortPowerDeniedCounter,
       pethPsePortOverLoadCounter,
       pethPsePortShortCounter,
       pethPsePortType,
       pethPsePortPowerClassifications
    }
    STATUS  current
    ::= { pethGroups 1 }

pethMainPseGroup OBJECT-GROUP
    OBJECTS {
       pethMainPsePower,
       pethMainPseOperStatus,
       pethMainPseConsumptionPower,
       pethMainPseUsageThreshold
    }
    STATUS  current
    ::= { pethGroups 2 }

pethNotificationControlGroup OBJECT-GROUP





    OBJECTS {
       pethNotificationControlEnable
    }
    STATUS  current
    ::= { pethGroups 3 }

pethPsePortNotificationGroup NOTIFICATION-GROUP
    NOTIFICATIONS { pethPsePortOnOffNotification}
    STATUS           current
    ::= { pethGroups 4 }

  pethMainPowerNotificationGroup NOTIFICATION-GROUP
     NOTIFICATIONS { pethMainPowerUsageOnNotification,
                      pethMainPowerUsageOffNotification}
    STATUS           current
      ::= { pethGroups 5 }

END

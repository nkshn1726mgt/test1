SYSAPPL-MIB DEFINITIONS ::= BEGIN

   IMPORTS
       MODULE-IDENTITY, OBJECT-TYPE,
       Unsigned32, TimeTicks, Counter32, Gauge32
           FROM SNMPv2-SMI
       DateAndTime, TEXTUAL-CONVENTION
           FROM SNMPv2-TC
       MODULE-COMPLIANCE, OBJECT-GROUP
           FROM SNMPv2-CONF
       mib-2 FROM SNMPv2-SMI;







   sysApplMIB MODULE-IDENTITY
       LAST-UPDATED "9710200000Z"
       ORGANIZATION "IETF Applications MIB Working Group"
       ::= { mib-2 54  }


   sysApplOBJ               OBJECT IDENTIFIER ::= { sysApplMIB 1 }
   sysApplInstalled         OBJECT IDENTIFIER ::= { sysApplOBJ 1 }
   sysApplRun               OBJECT IDENTIFIER ::= { sysApplOBJ 2 }
   sysApplMap               OBJECT IDENTIFIER ::= { sysApplOBJ 3 }
   sysApplNotifications     OBJECT IDENTIFIER ::= { sysApplMIB 2 }
   sysApplConformance       OBJECT IDENTIFIER ::= { sysApplMIB 3 }


   RunState ::= TEXTUAL-CONVENTION
       STATUS      current
       SYNTAX      INTEGER {
                   running (1),
                   runnable (2), -- waiting for resource (CPU, etc.)
                   waiting (3),  -- waiting for event
                   exiting (4),
                   other (5)     -- other invalid state
                   }

 LongUtf8String ::= TEXTUAL-CONVENTION
         DISPLAY-HINT "1024a"
         STATUS  current
         SYNTAX  OCTET STRING (SIZE (0..1024))

 Utf8String ::= TEXTUAL-CONVENTION
         DISPLAY-HINT "255a"
         STATUS  current
         SYNTAX  OCTET STRING (SIZE (0..255))










   sysApplInstallPkgTable OBJECT-TYPE
       SYNTAX      SEQUENCE OF SysApplInstallPkgEntry
       MAX-ACCESS  not-accessible
       STATUS      current

       ::= { sysApplInstalled 1 }

   sysApplInstallPkgEntry OBJECT-TYPE
       SYNTAX      SysApplInstallPkgEntry
       MAX-ACCESS  not-accessible
       STATUS      current
       INDEX    { sysApplInstallPkgIndex }
       ::= { sysApplInstallPkgTable 1 }

   SysApplInstallPkgEntry ::= SEQUENCE {
       sysApplInstallPkgIndex               Unsigned32,
       sysApplInstallPkgManufacturer        Utf8String,
       sysApplInstallPkgProductName         Utf8String,
       sysApplInstallPkgVersion             Utf8String,
       sysApplInstallPkgSerialNumber        Utf8String,
       sysApplInstallPkgDate                DateAndTime,
       sysApplInstallPkgLocation            LongUtf8String
   }

   sysApplInstallPkgIndex OBJECT-TYPE
       SYNTAX      Unsigned32 (1..'ffffffff'h)





       MAX-ACCESS  not-accessible
       STATUS      current
       ::= { sysApplInstallPkgEntry 1 }

   sysApplInstallPkgManufacturer OBJECT-TYPE
       SYNTAX      Utf8String
       MAX-ACCESS  read-only
       STATUS      current
       ::= { sysApplInstallPkgEntry 2 }

   sysApplInstallPkgProductName OBJECT-TYPE
       SYNTAX      Utf8String
       MAX-ACCESS  read-only
       STATUS      current
       ::= { sysApplInstallPkgEntry 3 }

   sysApplInstallPkgVersion OBJECT-TYPE
       SYNTAX      Utf8String
       MAX-ACCESS  read-only
       STATUS      current
       ::= { sysApplInstallPkgEntry 4 }

   sysApplInstallPkgSerialNumber OBJECT-TYPE
       SYNTAX      Utf8String
       MAX-ACCESS  read-only
       STATUS      current





       ::= { sysApplInstallPkgEntry 5 }

   sysApplInstallPkgDate OBJECT-TYPE
       SYNTAX      DateAndTime
       MAX-ACCESS  read-only
       STATUS      current
       ::= { sysApplInstallPkgEntry 6 }

   sysApplInstallPkgLocation OBJECT-TYPE
       SYNTAX      LongUtf8String
       MAX-ACCESS  read-only
       STATUS      current
       ::= { sysApplInstallPkgEntry 7 }



   sysApplInstallElmtTable OBJECT-TYPE
       SYNTAX      SEQUENCE OF SysApplInstallElmtEntry
       MAX-ACCESS  not-accessible
       STATUS      current





       ::= { sysApplInstalled 2 }

   sysApplInstallElmtEntry OBJECT-TYPE
       SYNTAX      SysApplInstallElmtEntry
       MAX-ACCESS  not-accessible
       STATUS      current
       INDEX    {sysApplInstallPkgIndex, sysApplInstallElmtIndex}
       ::= { sysApplInstallElmtTable 1 }

   SysApplInstallElmtEntry ::= SEQUENCE {
       sysApplInstallElmtIndex                 Unsigned32,
       sysApplInstallElmtName                  Utf8String,
       sysApplInstallElmtType                  INTEGER,
       sysApplInstallElmtDate                  DateAndTime,
       sysApplInstallElmtPath                  LongUtf8String,
       sysApplInstallElmtSizeHigh              Unsigned32,
       sysApplInstallElmtSizeLow               Unsigned32,
       sysApplInstallElmtRole                  BITS,
       sysApplInstallElmtModifyDate            DateAndTime,
       sysApplInstallElmtCurSizeHigh           Unsigned32,
       sysApplInstallElmtCurSizeLow            Unsigned32

   }

   sysApplInstallElmtIndex OBJECT-TYPE
       SYNTAX      Unsigned32 (1..'ffffffff'h)
       MAX-ACCESS  not-accessible
       STATUS      current
       ::= { sysApplInstallElmtEntry 1 }


   sysApplInstallElmtName OBJECT-TYPE
       SYNTAX      Utf8String
       MAX-ACCESS  read-only
       STATUS      current
       ::= { sysApplInstallElmtEntry 2 }






   sysApplInstallElmtType OBJECT-TYPE
       SYNTAX      INTEGER {
                   unknown(1),
                   nonexecutable(2),
                   operatingSystem(3),  -- executable
                   deviceDriver(4),     -- executable
                   application(5)       -- executable
                   }
       MAX-ACCESS  read-only
       STATUS      current
       ::= { sysApplInstallElmtEntry 3 }

   sysApplInstallElmtDate OBJECT-TYPE
       SYNTAX      DateAndTime
       MAX-ACCESS  read-only
       STATUS      current
       ::= { sysApplInstallElmtEntry 4 }

   sysApplInstallElmtPath OBJECT-TYPE
       SYNTAX      LongUtf8String
       MAX-ACCESS  read-only
       STATUS      current
       ::= { sysApplInstallElmtEntry 5}

   sysApplInstallElmtSizeHigh OBJECT-TYPE
       SYNTAX      Unsigned32
       MAX-ACCESS  read-only
       STATUS      current





       ::= { sysApplInstallElmtEntry 6 }

   sysApplInstallElmtSizeLow OBJECT-TYPE
       SYNTAX      Unsigned32
       MAX-ACCESS  read-only
       STATUS      current
       ::= { sysApplInstallElmtEntry 7 }

   sysApplInstallElmtRole  OBJECT-TYPE
       SYNTAX      BITS {
                   executable(0),
                   exclusive(1),
                   primary(2),
                   required(3),





                   dependent(4),
                   unknown(5)
                   }
       MAX-ACCESS  read-write
       STATUS      current

       DEFVAL { { unknown } }
       ::= { sysApplInstallElmtEntry 8 }

   sysApplInstallElmtModifyDate OBJECT-TYPE
       SYNTAX      DateAndTime
       MAX-ACCESS  read-only
       STATUS      current
       ::= { sysApplInstallElmtEntry 9 }

   sysApplInstallElmtCurSizeHigh OBJECT-TYPE
       SYNTAX      Unsigned32
       MAX-ACCESS  read-only
       STATUS      current
       ::= { sysApplInstallElmtEntry 10 }

   sysApplInstallElmtCurSizeLow OBJECT-TYPE
       SYNTAX      Unsigned32
       MAX-ACCESS  read-only
       STATUS      current
       ::= { sysApplInstallElmtEntry 11 }





   sysApplRunTable OBJECT-TYPE
       SYNTAX      SEQUENCE OF SysApplRunEntry
       MAX-ACCESS  not-accessible
       STATUS      current
       ::= { sysApplRun 1 }

   sysApplRunEntry OBJECT-TYPE
       SYNTAX      SysApplRunEntry





       MAX-ACCESS  not-accessible
       STATUS      current
       INDEX    { sysApplInstallPkgIndex, sysApplRunIndex }
       ::= { sysApplRunTable   1 }

   SysApplRunEntry ::= SEQUENCE {
       sysApplRunIndex                         Unsigned32,
       sysApplRunStarted                       DateAndTime,
       sysApplRunCurrentState                  RunState
   }

   sysApplRunIndex OBJECT-TYPE
       SYNTAX      Unsigned32 (1..'ffffffff'h)
       MAX-ACCESS  not-accessible
       STATUS      current
       ::= { sysApplRunEntry 1 }

   sysApplRunStarted OBJECT-TYPE
       SYNTAX      DateAndTime
       MAX-ACCESS  read-only
       STATUS      current
       ::= { sysApplRunEntry 2 }

   sysApplRunCurrentState OBJECT-TYPE
       SYNTAX      RunState
       MAX-ACCESS  read-only
       STATUS      current
       ::= { sysApplRunEntry 3 }








   sysApplPastRunTable OBJECT-TYPE
       SYNTAX      SEQUENCE OF SysApplPastRunEntry
       MAX-ACCESS  not-accessible
       STATUS      current
       ::= { sysApplRun 2 }

   sysApplPastRunEntry OBJECT-TYPE
       SYNTAX      SysApplPastRunEntry
       MAX-ACCESS  not-accessible
       STATUS      current
       INDEX    { sysApplInstallPkgIndex, sysApplPastRunIndex }
       ::= { sysApplPastRunTable   1 }

   SysApplPastRunEntry ::= SEQUENCE {
       sysApplPastRunIndex                     Unsigned32,
       sysApplPastRunStarted                   DateAndTime,
       sysApplPastRunExitState                 INTEGER,
       sysApplPastRunTimeEnded                 DateAndTime
   }

   sysApplPastRunIndex OBJECT-TYPE
       SYNTAX      Unsigned32 (1..'ffffffff'h)
       MAX-ACCESS  not-accessible
       STATUS      current
       ::= { sysApplPastRunEntry 1 }

   sysApplPastRunStarted OBJECT-TYPE
       SYNTAX      DateAndTime
       MAX-ACCESS  read-only
       STATUS      current
       ::= { sysApplPastRunEntry 2 }

   sysApplPastRunExitState OBJECT-TYPE
       SYNTAX      INTEGER {
                   complete (1), -- normal exit at sysApplRunTimeEnded
                   failed (2),   -- abnormal exit
                   other (3)
                   }
       MAX-ACCESS  read-only
       STATUS      current
       ::= { sysApplPastRunEntry 3 }

   sysApplPastRunTimeEnded OBJECT-TYPE
       SYNTAX      DateAndTime
       MAX-ACCESS  read-only
       STATUS      current
       ::= { sysApplPastRunEntry 4 }



   sysApplElmtRunTable OBJECT-TYPE
       SYNTAX      SEQUENCE OF SysApplElmtRunEntry
       MAX-ACCESS  not-accessible
       STATUS      current
       ::= { sysApplRun 3 }

   sysApplElmtRunEntry OBJECT-TYPE
       SYNTAX      SysApplElmtRunEntry
       MAX-ACCESS  not-accessible
       STATUS      current
       INDEX    { sysApplElmtRunInstallPkg, sysApplElmtRunInvocID,
                  sysApplElmtRunIndex }
       ::= { sysApplElmtRunTable   1 }

   SysApplElmtRunEntry ::= SEQUENCE {
       sysApplElmtRunInstallPkg        Unsigned32,
       sysApplElmtRunInvocID           Unsigned32,
       sysApplElmtRunIndex             Unsigned32,
       sysApplElmtRunInstallID         Unsigned32,
       sysApplElmtRunTimeStarted       DateAndTime,
       sysApplElmtRunState             RunState,
       sysApplElmtRunName              LongUtf8String,
       sysApplElmtRunParameters        Utf8String,
       sysApplElmtRunCPU               TimeTicks,
       sysApplElmtRunMemory            Gauge32,
       sysApplElmtRunNumFiles          Gauge32,
       sysApplElmtRunUser              Utf8String
   }

   sysApplElmtRunInstallPkg OBJECT-TYPE
       SYNTAX      Unsigned32 (0..'ffffffff'h)
       MAX-ACCESS  not-accessible
       STATUS      current
       ::= { sysApplElmtRunEntry 1 }

   sysApplElmtRunInvocID OBJECT-TYPE
       SYNTAX      Unsigned32 (0..'ffffffff'h)
       MAX-ACCESS  not-accessible
       STATUS      current
       ::= { sysApplElmtRunEntry 2 }

   sysApplElmtRunIndex OBJECT-TYPE
       SYNTAX      Unsigned32 (0..'ffffffff'h)
       MAX-ACCESS  not-accessible
       STATUS      current
       ::= { sysApplElmtRunEntry 3 }


   sysApplElmtRunInstallID OBJECT-TYPE
       SYNTAX      Unsigned32 (0..'ffffffff'h)
       MAX-ACCESS  read-only
       STATUS      current
       ::= { sysApplElmtRunEntry 4 }

   sysApplElmtRunTimeStarted OBJECT-TYPE
       SYNTAX      DateAndTime
       MAX-ACCESS  read-only
       STATUS      current
       ::= { sysApplElmtRunEntry 5 }

   sysApplElmtRunState OBJECT-TYPE
       SYNTAX      RunState
       MAX-ACCESS  read-only
       STATUS      current
       ::= { sysApplElmtRunEntry 6 }

   sysApplElmtRunName OBJECT-TYPE
       SYNTAX      LongUtf8String
       MAX-ACCESS  read-only
       STATUS      current
       ::= { sysApplElmtRunEntry 7 }

   sysApplElmtRunParameters OBJECT-TYPE
       SYNTAX      Utf8String
       MAX-ACCESS  read-only
       STATUS      current
   ::= { sysApplElmtRunEntry 8 }

   sysApplElmtRunCPU OBJECT-TYPE
       SYNTAX      TimeTicks
       MAX-ACCESS  read-only





       STATUS      current
       ::= { sysApplElmtRunEntry 9 }

   sysApplElmtRunMemory OBJECT-TYPE
       SYNTAX      Gauge32
       UNITS       "Kbytes"
       MAX-ACCESS  read-only
       STATUS      current

       ::= { sysApplElmtRunEntry 10 }

   sysApplElmtRunNumFiles OBJECT-TYPE
       SYNTAX      Gauge32
       MAX-ACCESS  read-only
       STATUS      current
       ::= { sysApplElmtRunEntry 11 }

   sysApplElmtRunUser OBJECT-TYPE
       SYNTAX      Utf8String
       MAX-ACCESS  read-only
       STATUS      current
       ::= { sysApplElmtRunEntry 12 }








   sysApplElmtPastRunTable OBJECT-TYPE
       SYNTAX      SEQUENCE OF SysApplElmtPastRunEntry
       MAX-ACCESS  not-accessible
       STATUS      current
       ::= { sysApplRun 4 }

   sysApplElmtPastRunEntry OBJECT-TYPE
       SYNTAX      SysApplElmtPastRunEntry
       MAX-ACCESS  not-accessible
       STATUS      current
       INDEX    { sysApplInstallPkgIndex, sysApplElmtPastRunInvocID,
                  sysApplElmtPastRunIndex }
       ::= { sysApplElmtPastRunTable   1 }

   SysApplElmtPastRunEntry ::= SEQUENCE {
       sysApplElmtPastRunInvocID           Unsigned32,
       sysApplElmtPastRunIndex             Unsigned32,
       sysApplElmtPastRunInstallID         Unsigned32,
       sysApplElmtPastRunTimeStarted       DateAndTime,
       sysApplElmtPastRunTimeEnded         DateAndTime,
       sysApplElmtPastRunName              LongUtf8String,
       sysApplElmtPastRunParameters        Utf8String,
       sysApplElmtPastRunCPU               TimeTicks,
       sysApplElmtPastRunMemory            Unsigned32,
       sysApplElmtPastRunNumFiles          Unsigned32,
       sysApplElmtPastRunUser              Utf8String
   }

   sysApplElmtPastRunInvocID OBJECT-TYPE
       SYNTAX      Unsigned32 (1..'ffffffff'h)
       MAX-ACCESS  not-accessible
       STATUS      current
       ::= { sysApplElmtPastRunEntry 1 }

   sysApplElmtPastRunIndex OBJECT-TYPE
       SYNTAX      Unsigned32 (0..'ffffffff'h)
       MAX-ACCESS  not-accessible
       STATUS      current
       ::= { sysApplElmtPastRunEntry 2 }


   sysApplElmtPastRunInstallID OBJECT-TYPE
       SYNTAX      Unsigned32 (1..'ffffffff'h)
       MAX-ACCESS  read-only
       STATUS      current
       ::= { sysApplElmtPastRunEntry 3 }

   sysApplElmtPastRunTimeStarted OBJECT-TYPE
       SYNTAX      DateAndTime
       MAX-ACCESS  read-only





       STATUS      current
       ::= { sysApplElmtPastRunEntry 4 }

   sysApplElmtPastRunTimeEnded OBJECT-TYPE
       SYNTAX      DateAndTime
       MAX-ACCESS  read-only
       STATUS      current
       ::= { sysApplElmtPastRunEntry 5 }

   sysApplElmtPastRunName OBJECT-TYPE
       SYNTAX      LongUtf8String
       MAX-ACCESS  read-only
       STATUS      current
       ::= { sysApplElmtPastRunEntry 6 }

   sysApplElmtPastRunParameters OBJECT-TYPE
       SYNTAX      Utf8String
       MAX-ACCESS  read-only
       STATUS      current
       ::= { sysApplElmtPastRunEntry 7 }

   sysApplElmtPastRunCPU OBJECT-TYPE
       SYNTAX      TimeTicks
       MAX-ACCESS  read-only
       STATUS      current
       ::= { sysApplElmtPastRunEntry 8 }

   sysApplElmtPastRunMemory OBJECT-TYPE
       SYNTAX      Unsigned32 (0..'ffffffff'h)
       UNITS       "Kbytes"
       MAX-ACCESS  read-only





       STATUS      current
       ::= { sysApplElmtPastRunEntry 9 }

   sysApplElmtPastRunNumFiles OBJECT-TYPE
       SYNTAX      Unsigned32 (0..'ffffffff'h)
       MAX-ACCESS  read-only
       STATUS      current
       ::= { sysApplElmtPastRunEntry 10 }

   sysApplElmtPastRunUser OBJECT-TYPE
       SYNTAX      Utf8String
       MAX-ACCESS  read-only
       STATUS      current
       ::= { sysApplElmtPastRunEntry 11 }



   sysApplPastRunMaxRows OBJECT-TYPE
       SYNTAX      Unsigned32 (0..'ffffffff'h)
       MAX-ACCESS  read-write
       STATUS      current





       DEFVAL      { 500 }
       ::= { sysApplRun 5 }

   sysApplPastRunTableRemItems OBJECT-TYPE
       SYNTAX      Counter32
       MAX-ACCESS  read-only
       STATUS      current
       ::= { sysApplRun 6 }

   sysApplPastRunTblTimeLimit OBJECT-TYPE
       SYNTAX      Unsigned32 (0..'ffffffff'h)
       UNITS       "seconds"
       MAX-ACCESS  read-write
       STATUS      current
       DEFVAL      { 7200 }
       ::= { sysApplRun 7 }

   sysApplElemPastRunMaxRows OBJECT-TYPE
       SYNTAX      Unsigned32 (0..'ffffffff'h)
       MAX-ACCESS  read-write
       STATUS      current
       DEFVAL      { 500 }
       ::= { sysApplRun 8 }

   sysApplElemPastRunTableRemItems OBJECT-TYPE
       SYNTAX      Counter32
       MAX-ACCESS  read-only
       STATUS      current
       ::= { sysApplRun 9 }

   sysApplElemPastRunTblTimeLimit OBJECT-TYPE
       SYNTAX      Unsigned32 (0..'ffffffff'h)
       UNITS       "seconds"
       MAX-ACCESS  read-write
       STATUS      current
       DEFVAL      { 7200 }
       ::= { sysApplRun 10 }

   sysApplAgentPollInterval  OBJECT-TYPE
       SYNTAX      Unsigned32 (0..'ffffffff'h)
       UNITS       "seconds"
       MAX-ACCESS  read-write
       STATUS      current
       DEFVAL      { 60 }
       ::= { sysApplRun 11 }








   sysApplMapTable OBJECT-TYPE
       SYNTAX      SEQUENCE OF SysApplMapEntry
       MAX-ACCESS  not-accessible
       STATUS      current
       ::= { sysApplMap 1 }

   sysApplMapEntry OBJECT-TYPE
       SYNTAX      SysApplMapEntry
       MAX-ACCESS  not-accessible
       STATUS      current
       INDEX  { sysApplElmtRunIndex, sysApplElmtRunInvocID,
                sysApplMapInstallElmtIndex }
       ::= { sysApplMapTable 1 }

   SysApplMapEntry ::= SEQUENCE {
       sysApplMapInstallElmtIndex    Unsigned32,
       sysApplMapInstallPkgIndex     Unsigned32
   }

   sysApplMapInstallElmtIndex OBJECT-TYPE
       SYNTAX      Unsigned32 (0..'ffffffff'h)
       MAX-ACCESS  not-accessible
       STATUS      current
       ::= { sysApplMapEntry 1 }

   sysApplMapInstallPkgIndex OBJECT-TYPE
       SYNTAX      Unsigned32 (0..'ffffffff'h)
       MAX-ACCESS  read-only
       STATUS      current
       ::= { sysApplMapEntry 2 }







   sysApplMIBCompliances  OBJECT IDENTIFIER ::= { sysApplConformance 1 }
   sysApplMIBGroups       OBJECT IDENTIFIER ::= { sysApplConformance 2 }

   sysApplMIBCompliance MODULE-COMPLIANCE
       STATUS  current
       MODULE  -- this module
           MANDATORY-GROUPS { sysApplInstalledGroup,
                              sysApplRunGroup, sysApplMapGroup }
       ::= { sysApplMIBCompliances 1 }

   sysApplInstalledGroup OBJECT-GROUP
       OBJECTS { sysApplInstallPkgManufacturer,
                 sysApplInstallPkgProductName,
                 sysApplInstallPkgVersion,
                 sysApplInstallPkgSerialNumber,
                 sysApplInstallPkgDate,
                 sysApplInstallPkgLocation,
                 sysApplInstallElmtName,
                 sysApplInstallElmtType,
                 sysApplInstallElmtDate,
                 sysApplInstallElmtPath,
                 sysApplInstallElmtSizeHigh,
                 sysApplInstallElmtSizeLow,
                 sysApplInstallElmtRole,
                 sysApplInstallElmtModifyDate,
                 sysApplInstallElmtCurSizeHigh,
                 sysApplInstallElmtCurSizeLow }
       STATUS  current
       ::= { sysApplMIBGroups 1 }

   sysApplRunGroup OBJECT-GROUP
       OBJECTS { sysApplRunStarted,
                 sysApplRunCurrentState,
                 sysApplPastRunStarted,
                 sysApplPastRunExitState,
                 sysApplPastRunTimeEnded,
                 sysApplElmtRunInstallID,
                 sysApplElmtRunTimeStarted,
                 sysApplElmtRunState,
                 sysApplElmtRunName,
                 sysApplElmtRunParameters,





                 sysApplElmtRunCPU,
                 sysApplElmtRunMemory,
                 sysApplElmtRunNumFiles,
                 sysApplElmtRunUser,
                 sysApplElmtPastRunInstallID,
                 sysApplElmtPastRunTimeStarted,
                 sysApplElmtPastRunTimeEnded,
                 sysApplElmtPastRunName,
                 sysApplElmtPastRunParameters,
                 sysApplElmtPastRunCPU,
                 sysApplElmtPastRunMemory,
                 sysApplElmtPastRunNumFiles,
                 sysApplElmtPastRunUser,
                 sysApplPastRunMaxRows,
                 sysApplPastRunTableRemItems,
                 sysApplPastRunTblTimeLimit,
                 sysApplElemPastRunMaxRows,
                 sysApplElemPastRunTableRemItems,
                 sysApplElemPastRunTblTimeLimit,
                 sysApplAgentPollInterval }
       STATUS  current
       ::= { sysApplMIBGroups 2 }

   sysApplMapGroup OBJECT-GROUP
       OBJECTS { sysApplMapInstallPkgIndex }
       STATUS  current
   ::= { sysApplMIBGroups 3 }

   END

VPN-TC-STD-MIB DEFINITIONS ::= BEGIN

   IMPORTS
       MODULE-IDENTITY, mib-2
           FROM SNMPv2-SMI

       TEXTUAL-CONVENTION
           FROM SNMPv2-TC;

   vpnTcMIB MODULE-IDENTITY
       LAST-UPDATED "200511150000Z"  -- 15 November 2005
       ORGANIZATION
           "Layer 3 Virtual Private Networks (L3VPN) Working Group."





       ::= { mib-2 129 }


   VPNId ::= TEXTUAL-CONVENTION
       STATUS current
       SYNTAX    OCTET STRING (SIZE (7))

   VPNIdOrZero ::= TEXTUAL-CONVENTION
       STATUS            current
       SYNTAX    OCTET STRING (SIZE (0 | 7))

   END

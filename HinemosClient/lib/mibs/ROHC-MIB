ROHC-MIB DEFINITIONS ::= BEGIN

  IMPORTS
      MODULE-IDENTITY, OBJECT-TYPE,
      Unsigned32, Counter32, mib-2
          FROM SNMPv2-SMI                                -- [RFC2578]

      TEXTUAL-CONVENTION, TruthValue,
      TimeInterval, DateAndTime
          FROM SNMPv2-TC                                 -- [RFC2579]

      MODULE-COMPLIANCE, OBJECT-GROUP
          FROM SNMPv2-CONF                               -- [RFC2580]

      SnmpAdminString
          FROM SNMP-FRAMEWORK-MIB                        -- [RFC3411]

      ifIndex
          FROM IF-MIB;                                   -- [RFC2863]

  rohcMIB MODULE-IDENTITY
      LAST-UPDATED "200406030000Z"  -- June 3, 2004
      ORGANIZATION "IETF Robust Header Compression Working Group"

      ::= { mib-2 112 }

  RohcChannelIdentifier ::= TEXTUAL-CONVENTION
      DISPLAY-HINT "d"
      STATUS       current
      SYNTAX       Unsigned32 (1..4294967295)

  RohcChannelIdentifierOrZero ::= TEXTUAL-CONVENTION
      DISPLAY-HINT "d"
      STATUS       current
      SYNTAX       Unsigned32 (0..4294967295)

  RohcCompressionRatio ::= TEXTUAL-CONVENTION
      DISPLAY-HINT "d"
      STATUS       current
      SYNTAX       Unsigned32


  rohcObjects       OBJECT IDENTIFIER ::= { rohcMIB 1 }
  rohcConformance   OBJECT IDENTIFIER ::= { rohcMIB 2 }


  rohcInstanceObjects       OBJECT IDENTIFIER ::= { rohcObjects 1 }


  rohcChannelTable OBJECT-TYPE
      SYNTAX      SEQUENCE OF RohcChannelEntry
      MAX-ACCESS  not-accessible
      STATUS      current
      ::= { rohcInstanceObjects 1 }

  rohcChannelEntry OBJECT-TYPE
      SYNTAX      RohcChannelEntry
      MAX-ACCESS  not-accessible
      STATUS      current
      INDEX { ifIndex, rohcChannelID }
      ::= { rohcChannelTable 1 }

  RohcChannelEntry ::= SEQUENCE {
      rohcChannelID               RohcChannelIdentifier,
      rohcChannelType             INTEGER,
      rohcChannelFeedbackFor      RohcChannelIdentifierOrZero,
      rohcChannelDescr            SnmpAdminString,
      rohcChannelStatus           INTEGER
  }

  rohcChannelID OBJECT-TYPE
      SYNTAX      RohcChannelIdentifier
      MAX-ACCESS  not-accessible
      STATUS      current
      ::= { rohcChannelEntry 2 }

  rohcChannelType OBJECT-TYPE
      SYNTAX      INTEGER {
                      notInUse(1),
                      rohc(2),
                      dedicatedFeedback(3)
                  }
      MAX-ACCESS  read-only
      STATUS      current





      ::= { rohcChannelEntry 3 }

  rohcChannelFeedbackFor OBJECT-TYPE
      SYNTAX      RohcChannelIdentifierOrZero
      MAX-ACCESS  read-only
      STATUS      current
      ::= { rohcChannelEntry 4 }

  rohcChannelDescr OBJECT-TYPE
      SYNTAX      SnmpAdminString
      MAX-ACCESS  read-only
      STATUS      current
      ::= { rohcChannelEntry 5 }

  rohcChannelStatus OBJECT-TYPE
      SYNTAX      INTEGER {
                      enabled(1),
                      disabled(2)
                  }
      MAX-ACCESS  read-only
      STATUS      current
      ::= { rohcChannelEntry 6 }







  rohcInstanceTable OBJECT-TYPE
      SYNTAX      SEQUENCE OF RohcInstanceEntry
      MAX-ACCESS  not-accessible
      STATUS      current
      ::= { rohcInstanceObjects 2 }

  rohcInstanceEntry OBJECT-TYPE
      SYNTAX      RohcInstanceEntry
      MAX-ACCESS  not-accessible
      STATUS      current
      INDEX { ifIndex, rohcInstanceType, rohcChannelID }
      ::= { rohcInstanceTable 1 }

  RohcInstanceEntry ::= SEQUENCE {
      rohcInstanceType               INTEGER,
      rohcInstanceFBChannelID        RohcChannelIdentifierOrZero,
      rohcInstanceVendor             OBJECT IDENTIFIER,
      rohcInstanceVersion            SnmpAdminString,
      rohcInstanceDescr              SnmpAdminString,
      rohcInstanceClockRes           Unsigned32,
      rohcInstanceMaxCID             Unsigned32,
      rohcInstanceLargeCIDs          TruthValue,
      rohcInstanceMRRU               Unsigned32,
      rohcInstanceContextStorageTime TimeInterval,
      rohcInstanceStatus             INTEGER,
      rohcInstanceContextsTotal      Counter32,
      rohcInstanceContextsCurrent    Unsigned32,
      rohcInstancePackets            Counter32,
      rohcInstanceIRs                Counter32,
      rohcInstanceIRDYNs             Counter32,
      rohcInstanceFeedbacks          Counter32,





      rohcInstanceCompressionRatio   RohcCompressionRatio
  }

  rohcInstanceType OBJECT-TYPE
      SYNTAX      INTEGER {
                      compressor(1),
                      decompressor(2)
                  }
      MAX-ACCESS  not-accessible
      STATUS      current
      ::= { rohcInstanceEntry 2 }

  rohcInstanceFBChannelID OBJECT-TYPE
      SYNTAX      RohcChannelIdentifierOrZero
      MAX-ACCESS  read-only
      STATUS      current
      ::= { rohcInstanceEntry 4 }

  rohcInstanceVendor OBJECT-TYPE
      SYNTAX      OBJECT IDENTIFIER
      MAX-ACCESS  read-only
      STATUS      current
      ::= { rohcInstanceEntry 5 }

  rohcInstanceVersion OBJECT-TYPE
      SYNTAX      SnmpAdminString (SIZE (0..32))
      MAX-ACCESS  read-only
      STATUS      current
      ::= { rohcInstanceEntry 6 }

  rohcInstanceDescr OBJECT-TYPE
      SYNTAX      SnmpAdminString
      MAX-ACCESS  read-only
      STATUS      current
      ::= { rohcInstanceEntry 7 }

  rohcInstanceClockRes OBJECT-TYPE
      SYNTAX      Unsigned32
      UNITS       "milliseconds"
      MAX-ACCESS  read-only
      STATUS      current
      ::= { rohcInstanceEntry 8 }

  rohcInstanceMaxCID OBJECT-TYPE
      SYNTAX      Unsigned32 (1..16383)
      MAX-ACCESS  read-only
      STATUS      current
      ::= { rohcInstanceEntry 9 }

  rohcInstanceLargeCIDs OBJECT-TYPE
      SYNTAX      TruthValue
      MAX-ACCESS  read-only
      STATUS      current





      ::= { rohcInstanceEntry 10 }

  rohcInstanceMRRU OBJECT-TYPE
      SYNTAX      Unsigned32
      MAX-ACCESS  read-only
      STATUS      current
      ::= { rohcInstanceEntry 11 }

  rohcInstanceContextStorageTime OBJECT-TYPE
      SYNTAX      TimeInterval
      UNITS       "centi-seconds"
      MAX-ACCESS  read-write
      STATUS      current
      DEFVAL { 360000 }
      ::= { rohcInstanceEntry 12 }

  rohcInstanceStatus OBJECT-TYPE
      SYNTAX      INTEGER {
                      enabled(1),
                      disabled(2)
                  }
      MAX-ACCESS  read-only
      STATUS      current





      ::= { rohcInstanceEntry 13 }

  rohcInstanceContextsTotal OBJECT-TYPE
      SYNTAX      Counter32
      MAX-ACCESS  read-only
      STATUS      current
      ::= { rohcInstanceEntry 14 }

  rohcInstanceContextsCurrent OBJECT-TYPE
      SYNTAX      Unsigned32
      MAX-ACCESS  read-only
      STATUS      current
      ::= { rohcInstanceEntry 15 }

  rohcInstancePackets OBJECT-TYPE
      SYNTAX      Counter32
      MAX-ACCESS  read-only
      STATUS      current
      ::= { rohcInstanceEntry 16 }

  rohcInstanceIRs OBJECT-TYPE
      SYNTAX      Counter32
      MAX-ACCESS  read-only
      STATUS      current
      ::= { rohcInstanceEntry 17 }

  rohcInstanceIRDYNs OBJECT-TYPE
      SYNTAX      Counter32
      MAX-ACCESS  read-only
      STATUS      current
      ::= { rohcInstanceEntry 18 }

  rohcInstanceFeedbacks OBJECT-TYPE
      SYNTAX      Counter32
      MAX-ACCESS  read-only
      STATUS      current
      ::= { rohcInstanceEntry 19 }

  rohcInstanceCompressionRatio OBJECT-TYPE
      SYNTAX      RohcCompressionRatio
      MAX-ACCESS  read-only
      STATUS      current
      ::= { rohcInstanceEntry 20 }







  rohcProfileTable OBJECT-TYPE
      SYNTAX      SEQUENCE OF RohcProfileEntry
      MAX-ACCESS  not-accessible
      STATUS      current
      ::= { rohcInstanceObjects 3 }

  rohcProfileEntry OBJECT-TYPE
      SYNTAX      RohcProfileEntry
      MAX-ACCESS  not-accessible
      STATUS      current
      INDEX { rohcChannelID, rohcProfile }
      ::= { rohcProfileTable 1 }

  RohcProfileEntry ::= SEQUENCE {
      rohcProfile            Unsigned32,
      rohcProfileVendor      OBJECT IDENTIFIER,
      rohcProfileVersion     SnmpAdminString,
      rohcProfileDescr       SnmpAdminString,
      rohcProfileNegotiated  TruthValue
  }

  rohcProfile OBJECT-TYPE
      SYNTAX      Unsigned32 (0..65535)
      MAX-ACCESS  not-accessible
      STATUS      current
      ::= { rohcProfileEntry 2 }

  rohcProfileVendor OBJECT-TYPE
      SYNTAX      OBJECT IDENTIFIER
      MAX-ACCESS  read-only
      STATUS      current





      ::= { rohcProfileEntry 3 }

  rohcProfileVersion OBJECT-TYPE
      SYNTAX      SnmpAdminString (SIZE (0..32))
      MAX-ACCESS  read-only
      STATUS      current
      ::= { rohcProfileEntry 4 }

  rohcProfileDescr OBJECT-TYPE
      SYNTAX      SnmpAdminString
      MAX-ACCESS  read-only
      STATUS      current
      ::= { rohcProfileEntry 5 }

  rohcProfileNegotiated OBJECT-TYPE
      SYNTAX      TruthValue
      MAX-ACCESS  read-only
      STATUS      current
      ::= { rohcProfileEntry 6 }


  rohcContextTable OBJECT-TYPE
      SYNTAX      SEQUENCE OF RohcContextEntry





      MAX-ACCESS  not-accessible
      STATUS      current
      ::= { rohcObjects 2 }

  rohcContextEntry OBJECT-TYPE
      SYNTAX      RohcContextEntry
      MAX-ACCESS  not-accessible
      STATUS      current
      INDEX {
          rohcChannelID,
          rohcContextCID
      }
      ::= { rohcContextTable 1 }

  RohcContextEntry ::= SEQUENCE {
      rohcContextCID                  Unsigned32,
      rohcContextCIDState             INTEGER,
      rohcContextProfile              Unsigned32,
      rohcContextDecompressorDepth    Unsigned32,
      rohcContextStorageTime          TimeInterval,
      rohcContextActivationTime       DateAndTime,
      rohcContextDeactivationTime     DateAndTime,
      rohcContextPackets              Counter32,
      rohcContextIRs                  Counter32,
      rohcContextIRDYNs               Counter32,
      rohcContextFeedbacks            Counter32,
      rohcContextDecompressorFailures Counter32,
      rohcContextDecompressorRepairs  Counter32,
      rohcContextAllPacketsRatio      RohcCompressionRatio,
      rohcContextAllHeadersRatio      RohcCompressionRatio,
      rohcContextAllPacketsMeanSize   Unsigned32,
      rohcContextAllHeadersMeanSize   Unsigned32,
      rohcContextLastPacketsRatio     RohcCompressionRatio,
      rohcContextLastHeadersRatio     RohcCompressionRatio,
      rohcContextLastPacketsMeanSize  Unsigned32,
      rohcContextLastHeadersMeanSize  Unsigned32
  }

  rohcContextCID OBJECT-TYPE
      SYNTAX      Unsigned32 (0..16383)
      MAX-ACCESS  not-accessible
      STATUS      current
      ::= { rohcContextEntry 2 }

  rohcContextCIDState OBJECT-TYPE
      SYNTAX      INTEGER {
                      unused(1),
                      active(2),
                      expired(3),
                      terminated(4)
                  }
      MAX-ACCESS  read-only
      STATUS      current
      ::= { rohcContextEntry 3 }

  rohcContextProfile OBJECT-TYPE
      SYNTAX      Unsigned32 (0..65535)
      MAX-ACCESS  read-only
      STATUS      current
      ::= { rohcContextEntry 4 }

  rohcContextDecompressorDepth OBJECT-TYPE
      SYNTAX      Unsigned32
      MAX-ACCESS  read-only
      STATUS      current
      ::= { rohcContextEntry 5 }

  rohcContextStorageTime OBJECT-TYPE
      SYNTAX      TimeInterval
      UNITS       "centi-seconds"
      MAX-ACCESS  read-write
      STATUS      current
      ::= { rohcContextEntry 6 }

  rohcContextActivationTime OBJECT-TYPE
      SYNTAX      DateAndTime
      MAX-ACCESS  read-only
      STATUS      current





      DEFVAL { '0000000000000000'H }
      ::= { rohcContextEntry 7 }

  rohcContextDeactivationTime OBJECT-TYPE
      SYNTAX      DateAndTime
      MAX-ACCESS  read-only
      STATUS      current
      DEFVAL { '0000000000000000'H }
      ::= { rohcContextEntry 8 }

  rohcContextPackets OBJECT-TYPE
      SYNTAX      Counter32
      MAX-ACCESS  read-only
      STATUS      current
      ::= { rohcContextEntry 9 }

  rohcContextIRs OBJECT-TYPE
      SYNTAX      Counter32
      MAX-ACCESS  read-only
      STATUS      current
      ::= { rohcContextEntry 10 }

  rohcContextIRDYNs OBJECT-TYPE
      SYNTAX      Counter32
      MAX-ACCESS  read-only
      STATUS      current
      ::= { rohcContextEntry 11 }

  rohcContextFeedbacks OBJECT-TYPE
      SYNTAX      Counter32
      MAX-ACCESS  read-only
      STATUS      current
      ::= { rohcContextEntry 12 }

  rohcContextDecompressorFailures OBJECT-TYPE
      SYNTAX      Counter32
      MAX-ACCESS  read-only
      STATUS      current





      ::= { rohcContextEntry 13 }

  rohcContextDecompressorRepairs OBJECT-TYPE
      SYNTAX      Counter32
      MAX-ACCESS  read-only
      STATUS      current
      ::= { rohcContextEntry 14 }

  rohcContextAllPacketsRatio OBJECT-TYPE
      SYNTAX      RohcCompressionRatio
      MAX-ACCESS  read-only
      STATUS      current
      ::= { rohcContextEntry 15 }

  rohcContextAllHeadersRatio OBJECT-TYPE
      SYNTAX      RohcCompressionRatio
      MAX-ACCESS  read-only





      STATUS      current
      ::= { rohcContextEntry 16 }

  rohcContextAllPacketsMeanSize OBJECT-TYPE
      SYNTAX      Unsigned32
      MAX-ACCESS  read-only
      STATUS      current
      ::= { rohcContextEntry 17 }

  rohcContextAllHeadersMeanSize OBJECT-TYPE
      SYNTAX      Unsigned32
      MAX-ACCESS  read-only
      STATUS      current
      ::= { rohcContextEntry 18 }

  rohcContextLastPacketsRatio OBJECT-TYPE
      SYNTAX      RohcCompressionRatio
      MAX-ACCESS  read-only
      STATUS      current
      ::= { rohcContextEntry 19 }

  rohcContextLastHeadersRatio OBJECT-TYPE
      SYNTAX      RohcCompressionRatio
      MAX-ACCESS  read-only





      STATUS      current
      ::= { rohcContextEntry 20 }

  rohcContextLastPacketsMeanSize OBJECT-TYPE
      SYNTAX      Unsigned32
      MAX-ACCESS  read-only
      STATUS      current
      ::= { rohcContextEntry 21 }

  rohcContextLastHeadersMeanSize OBJECT-TYPE
      SYNTAX      Unsigned32
      MAX-ACCESS  read-only
      STATUS      current
      ::= { rohcContextEntry 22 }


  rohcCompliances OBJECT IDENTIFIER ::= { rohcConformance 1 }
  rohcGroups      OBJECT IDENTIFIER ::= { rohcConformance 2 }








  rohcCompliance MODULE-COMPLIANCE
      STATUS      current
      MODULE      -- this module
      MANDATORY-GROUPS {
              rohcInstanceGroup, rohcContextGroup
      }
      GROUP   rohcStatisticsGroup
      GROUP   rohcTimerGroup
      OBJECT  rohcInstanceContextStorageTime
      MIN-ACCESS  read-only
      OBJECT  rohcContextStorageTime
      MIN-ACCESS  read-only
      GROUP   rohcContextStatisticsGroup
      ::= { rohcCompliances 1 }

  rohcInstanceGroup OBJECT-GROUP
      OBJECTS {
          rohcChannelType,
          rohcChannelFeedbackFor,
          rohcChannelDescr,
          rohcChannelStatus,
          rohcInstanceFBChannelID,
          rohcInstanceVendor,





          rohcInstanceVersion,
          rohcInstanceDescr,
          rohcInstanceClockRes,
          rohcInstanceMaxCID,
          rohcInstanceLargeCIDs,
          rohcInstanceMRRU,
          rohcInstanceStatus,
          rohcProfileVendor,
          rohcProfileVersion,
          rohcProfileDescr,
          rohcProfileNegotiated
      }
      STATUS      current
      ::= { rohcGroups 2 }

  rohcStatisticsGroup OBJECT-GROUP
      OBJECTS {
          rohcInstanceContextsTotal,
          rohcInstanceContextsCurrent,
          rohcInstancePackets,
          rohcInstanceIRs,
          rohcInstanceIRDYNs,
          rohcInstanceFeedbacks,
          rohcInstanceCompressionRatio
      }
      STATUS      current
      ::= { rohcGroups 4 }

  rohcContextGroup OBJECT-GROUP
      OBJECTS {
          rohcContextCIDState,
          rohcContextProfile,
          rohcContextDecompressorDepth
      }
      STATUS      current
      ::= { rohcGroups 5 }

  rohcTimerGroup OBJECT-GROUP
      OBJECTS {
          rohcInstanceContextStorageTime,





          rohcContextStorageTime,
          rohcContextActivationTime,
          rohcContextDeactivationTime

      }
      STATUS      current
      ::= { rohcGroups 6 }

  rohcContextStatisticsGroup OBJECT-GROUP
      OBJECTS {
          rohcContextPackets,
          rohcContextIRs,
          rohcContextIRDYNs,
          rohcContextFeedbacks,
          rohcContextDecompressorFailures,
          rohcContextDecompressorRepairs,
          rohcContextAllPacketsRatio,
          rohcContextAllHeadersRatio,
          rohcContextAllPacketsMeanSize,
          rohcContextAllHeadersMeanSize,
          rohcContextLastPacketsRatio,
          rohcContextLastHeadersRatio,
          rohcContextLastPacketsMeanSize,
          rohcContextLastHeadersMeanSize
      }
      STATUS      current
      ::= { rohcGroups 7 }

  END

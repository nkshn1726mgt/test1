APPC-MIB DEFINITIONS        ::= BEGIN

IMPORTS
      DisplayString, InstancePointer, TEXTUAL-CONVENTION, DateAndTime
                FROM SNMPv2-TC

      mib-2, Counter32, Gauge32, Integer32, TimeTicks,
      OBJECT-TYPE, MODULE-IDENTITY
                FROM SNMPv2-SMI

      snanauMIB
                FROM SNA-NAU-MIB

      MODULE-COMPLIANCE, OBJECT-GROUP
                FROM SNMPv2-CONF;

appcMIB MODULE-IDENTITY
      LAST-UPDATED  "9512150000Z"
      ORGANIZATION  "IETF SNA NAU MIB Working Group"

::= { snanauMIB 3 }

appcObjects          OBJECT IDENTIFIER ::= { appcMIB 1 }
  appcGlobal         OBJECT IDENTIFIER ::= { appcObjects 1 }
  appcLu             OBJECT IDENTIFIER ::= { appcObjects 2 }
  appcTp             OBJECT IDENTIFIER ::= { appcObjects 3 }
  appcSession        OBJECT IDENTIFIER ::= { appcObjects 4 }
  appcConversation   OBJECT IDENTIFIER ::= { appcObjects 5 }
  appcCPIC           OBJECT IDENTIFIER ::= { appcObjects 6 }









SnaSenseData ::= TEXTUAL-CONVENTION
      STATUS current

      SYNTAX DisplayString (SIZE (8))

appcCntrlAdminGroup OBJECT IDENTIFIER ::= { appcGlobal 1 }

appcCntrlAdminStat OBJECT-TYPE
      SYNTAX INTEGER {
                      notActive(1),
                      active(2)
                     }
      MAX-ACCESS read-write
      STATUS current

      ::= { appcCntrlAdminGroup  1 }

appcCntrlAdminRscv OBJECT-TYPE
      SYNTAX INTEGER {
                      notActive(1),
                      active(2)
                     }
      MAX-ACCESS read-write
      STATUS current

      ::= { appcCntrlAdminGroup  2 }

appcCntrlAdminTrace OBJECT-TYPE
      SYNTAX INTEGER {
                      notActive(1),
                      active(2)
                     }
      MAX-ACCESS read-write
      STATUS current

      ::= { appcCntrlAdminGroup  3 }

appcCntrlAdminTraceParm OBJECT-TYPE
      SYNTAX DisplayString (SIZE (0..128))
      MAX-ACCESS read-write
      STATUS current

      ::= { appcCntrlAdminGroup  4 }






appcCntrlOperGroup OBJECT IDENTIFIER ::= { appcGlobal 2 }

appcCntrlOperStat OBJECT-TYPE
      SYNTAX INTEGER {
                      notActive(1),
                      active(2)
                     }
      MAX-ACCESS read-only
      STATUS current

      ::= { appcCntrlOperGroup 1 }

appcCntrlOperStatTime OBJECT-TYPE
      SYNTAX TimeTicks
      MAX-ACCESS read-only
      STATUS current

      ::= { appcCntrlOperGroup 2 }

appcCntrlOperRscv OBJECT-TYPE
      SYNTAX INTEGER {
                      notActive(1),
                      active(2)
                     }
      MAX-ACCESS read-only
      STATUS current






      ::= { appcCntrlOperGroup 3 }

appcCntrlOperRscvTime OBJECT-TYPE
      SYNTAX TimeTicks
      MAX-ACCESS read-only
      STATUS current

      ::= { appcCntrlOperGroup 4 }

appcCntrlOperTrace OBJECT-TYPE
      SYNTAX INTEGER {
                      notActive(1),
                      active(2)
                     }
      MAX-ACCESS read-only
      STATUS current

      ::= { appcCntrlOperGroup 5 }

appcCntrlOperTraceTime OBJECT-TYPE
      SYNTAX TimeTicks
      MAX-ACCESS read-only
      STATUS current

      ::= { appcCntrlOperGroup 6 }

appcCntrlOperTraceParm OBJECT-TYPE
      SYNTAX DisplayString (SIZE (0..128))
      MAX-ACCESS read-only
      STATUS current

      ::= { appcCntrlOperGroup 7 }






appcGlobalObjects OBJECT IDENTIFIER ::= { appcGlobal 3 }

appcUpTime OBJECT-TYPE
      SYNTAX TimeTicks
      MAX-ACCESS read-only
      STATUS current

      ::= { appcGlobalObjects 1 }

appcDefaultModeName OBJECT-TYPE
      SYNTAX DisplayString (SIZE (1..8))
      MAX-ACCESS read-only
      STATUS current

      ::= { appcGlobalObjects 2 }

appcDefaultLuName OBJECT-TYPE
      SYNTAX DisplayString (SIZE (1..17))
      MAX-ACCESS read-only
      STATUS current

      ::= { appcGlobalObjects 3 }

appcDefaultImplInbndPlu OBJECT-TYPE
      SYNTAX INTEGER {
                      no(1),
                      yes(2)
                     }
      MAX-ACCESS read-only
      STATUS current

      ::= { appcGlobalObjects 4 }

appcDefaultMaxMcLlSndSize OBJECT-TYPE
      SYNTAX Integer32
      MAX-ACCESS read-only
      STATUS current

      ::= { appcGlobalObjects 5 }






appcDefaultFileSpec OBJECT-TYPE
      SYNTAX DisplayString (SIZE (0..80))
      MAX-ACCESS read-only
      STATUS current

      ::= { appcGlobalObjects 6 }

appcDefaultTpOperation OBJECT-TYPE
      SYNTAX INTEGER {
                      other(1),
                      queuedOperatorStarted(2),
                      queuedOperatorPreloaded(3),
                      queuedAmStarted(4),
                      nonqueuedAmStarted(5)
                     }
      MAX-ACCESS read-only
      STATUS current

      ::= { appcGlobalObjects 7 }

appcDefaultTpConvSecRqd OBJECT-TYPE
      SYNTAX INTEGER {
                      no(1),
                      yes(2)
                     }
      MAX-ACCESS read-only
      STATUS current

      ::= { appcGlobalObjects 8 }

appcLocalCpName OBJECT-TYPE
      SYNTAX DisplayString (SIZE (0..17))
      MAX-ACCESS read-only
      STATUS current

      ::= { appcGlobalObjects 9 }

appcActiveSessions OBJECT-TYPE
      SYNTAX Gauge32
      MAX-ACCESS read-only
      STATUS current

      ::= { appcGlobalObjects 10 }

appcActiveHprSessions OBJECT-TYPE
      SYNTAX Gauge32
      MAX-ACCESS read-only
      STATUS current

      ::= { appcGlobalObjects 11 }

appcCnosControl OBJECT IDENTIFIER ::= { appcGlobal 4 }


appcCnosCommand OBJECT-TYPE
      SYNTAX INTEGER {
                      initSesslimit(1),
                      changeSesslimit(2),
                      resetSesslimit(3)
                     }
      MAX-ACCESS read-write
      STATUS current






      ::= { appcCnosControl 1 }

appcCnosMaxSessLimit OBJECT-TYPE
      SYNTAX Integer32
      MAX-ACCESS read-write
      STATUS current

      DEFVAL { 0 }

      ::= { appcCnosControl 2 }

appcCnosMinCwinLimit OBJECT-TYPE
      SYNTAX Integer32
      MAX-ACCESS read-write
      STATUS current

      DEFVAL { 0 }

      ::= { appcCnosControl 3 }

appcCnosMinClosLimit OBJECT-TYPE
      SYNTAX Integer32
      MAX-ACCESS read-write
      STATUS current






      DEFVAL { 0 }

      ::= { appcCnosControl 4 }

appcCnosDrainSelf OBJECT-TYPE
      SYNTAX INTEGER {
                      no(1),
                      yes(2)
                     }
      MAX-ACCESS read-write
      STATUS current

      DEFVAL { no }

      ::= { appcCnosControl 5 }

appcCnosDrainPart OBJECT-TYPE
      SYNTAX INTEGER {
                      no(1),
                      yes(2)
                     }
      MAX-ACCESS read-write
      STATUS current






      DEFVAL { yes }

      ::= { appcCnosControl 6 }

appcCnosResponsible OBJECT-TYPE
      SYNTAX INTEGER {
                      source(1),
                      target(2)
                     }
      MAX-ACCESS read-write
      STATUS current

      DEFVAL { source }

      ::= { appcCnosControl 7 }

appcCnosForce OBJECT-TYPE
      SYNTAX INTEGER {
                      no(1),
                      yes(2)
                     }
      MAX-ACCESS read-write
      STATUS current

      DEFVAL { no }

      ::= { appcCnosControl 8 }

appcCnosTargetLocLuName OBJECT-TYPE
      SYNTAX DisplayString (SIZE (1..17))
      MAX-ACCESS read-write
      STATUS current

      ::= { appcCnosControl 9 }

appcCnosTargetParLuName OBJECT-TYPE
      SYNTAX DisplayString (SIZE (1..17))
      MAX-ACCESS read-write
      STATUS current

      ::= { appcCnosControl 10 }

appcCnosTargetModeName OBJECT-TYPE
      SYNTAX DisplayString (SIZE (1..8))
      MAX-ACCESS read-write
      STATUS current

      ::= { appcCnosControl 11 }





appcLluAdminTable OBJECT-TYPE
      SYNTAX SEQUENCE OF AppcLluAdminEntry
      MAX-ACCESS not-accessible
      STATUS current

      ::= { appcLu 1 }

appcLluAdminEntry OBJECT-TYPE
      SYNTAX AppcLluAdminEntry
      MAX-ACCESS not-accessible
      STATUS current






      INDEX { appcLluAdminName }

      ::= { appcLluAdminTable 1 }

AppcLluAdminEntry     ::= SEQUENCE {
        appcLluAdminName               DisplayString,
        appcLluAdminDepType            INTEGER,
        appcLluAdminLocalAddress       OCTET STRING,
        appcLluAdminSessLimit          Integer32,
        appcLluAdminBindRspMayQ        INTEGER,
        appcLluAdminCompression        INTEGER,
        appcLluAdminInBoundCompLevel   INTEGER,
        appcLluAdminOutBoundCompLevel  INTEGER,
        appcLluAdminCompRleBeforeLZ    INTEGER,
        appcLluAdminAlias              DisplayString
                     }

appcLluAdminName OBJECT-TYPE
      SYNTAX DisplayString (SIZE (1..17))
      MAX-ACCESS not-accessible
      STATUS current

      ::= { appcLluAdminEntry 1 }

appcLluAdminDepType OBJECT-TYPE
      SYNTAX INTEGER {
                      dependent(1),
                      independent(2)
                     }
      MAX-ACCESS read-only
      STATUS current

      ::= { appcLluAdminEntry 2 }

appcLluAdminLocalAddress OBJECT-TYPE
      SYNTAX OCTET STRING (SIZE (1))
      MAX-ACCESS read-only
      STATUS current

      ::= { appcLluAdminEntry 3 }

appcLluAdminSessLimit OBJECT-TYPE
      SYNTAX Integer32
      MAX-ACCESS read-only
      STATUS current

      ::= { appcLluAdminEntry 4 }

appcLluAdminBindRspMayQ OBJECT-TYPE
      SYNTAX INTEGER {
                      no(1),
                      yes(2)
                     }
      MAX-ACCESS read-only
      STATUS current

      ::= { appcLluAdminEntry 5 }

appcLluAdminCompression OBJECT-TYPE
      SYNTAX INTEGER {
                      prohibited(1),
                      required(2),
                      negotiable(3)
                     }
      MAX-ACCESS read-only
      STATUS current

      ::= { appcLluAdminEntry 6 }





appcLluAdminInBoundCompLevel OBJECT-TYPE
      SYNTAX INTEGER {
                      none(1),
                      rle(2),
                      lz9(3),
                      lz10(4),
                      lz12(5)
                     }
      MAX-ACCESS read-only
      STATUS current

      ::= { appcLluAdminEntry 7 }

appcLluAdminOutBoundCompLevel OBJECT-TYPE
      SYNTAX INTEGER {
                      none(1),
                      rle(2),
                      lz9(3),
                      lz10(4),
                      lz12(5)
                     }
      MAX-ACCESS read-only
      STATUS current

      ::= { appcLluAdminEntry 8 }

appcLluAdminCompRleBeforeLZ OBJECT-TYPE
      SYNTAX INTEGER {
                      no(1),
                      yes(2)
                     }
      MAX-ACCESS read-only
      STATUS current

      ::= { appcLluAdminEntry 9 }

appcLluAdminAlias OBJECT-TYPE
      SYNTAX DisplayString (SIZE (0..8))
      MAX-ACCESS read-only
      STATUS current

      ::= { appcLluAdminEntry 10 }








appcLluOperTable OBJECT-TYPE
      SYNTAX SEQUENCE OF AppcLluOperEntry
      MAX-ACCESS not-accessible
      STATUS current
      ::= { appcLu 2 }

appcLluOperEntry OBJECT-TYPE
      SYNTAX AppcLluOperEntry
      MAX-ACCESS not-accessible
      STATUS current

      INDEX { appcLluOperName }

      ::= { appcLluOperTable 1 }

AppcLluOperEntry     ::= SEQUENCE {
        appcLluOperName               DisplayString,
        appcLluOperDepType            INTEGER,
        appcLluOperLocalAddress       OCTET STRING,
        appcLluOperSessLimit          Integer32,
        appcLluOperBindRspMayQ        INTEGER,
        appcLluOperCompression        INTEGER,
        appcLluOperInBoundCompLevel   INTEGER,
        appcLluOperOutBoundCompLevel  INTEGER,
        appcLluOperCompRleBeforeLZ    INTEGER,
        appcLluOperAlias              DisplayString,
        appcLluOperActiveSessions     Gauge32
                     }

appcLluOperName OBJECT-TYPE
      SYNTAX DisplayString (SIZE (1..17))
      MAX-ACCESS not-accessible
      STATUS current

      ::= { appcLluOperEntry 1 }






appcLluOperDepType OBJECT-TYPE
      SYNTAX INTEGER {
                      dependent(1),
                      independent(2)
                     }
      MAX-ACCESS read-only
      STATUS current

      ::= { appcLluOperEntry 2 }

appcLluOperLocalAddress OBJECT-TYPE
      SYNTAX OCTET STRING (SIZE (1))
      MAX-ACCESS read-only
      STATUS current

      ::= { appcLluOperEntry 3 }

appcLluOperSessLimit OBJECT-TYPE
      SYNTAX Integer32
      MAX-ACCESS read-only
      STATUS current

      ::= { appcLluOperEntry 4 }

appcLluOperBindRspMayQ OBJECT-TYPE
      SYNTAX INTEGER {
                      no(1),
                      yes(2)
                     }
      MAX-ACCESS read-only
      STATUS current

      ::= { appcLluOperEntry 5 }






appcLluOperCompression OBJECT-TYPE
      SYNTAX INTEGER {
                      prohibited(1),
                      required(2),
                      negotiable(3)
                     }
      MAX-ACCESS read-only
      STATUS current

      ::= { appcLluOperEntry 6 }

appcLluOperInBoundCompLevel OBJECT-TYPE
      SYNTAX INTEGER {
                      none(1),
                      rle(2),
                      lz9(3),
                      lz10(4),
                      lz12(5)
                     }
      MAX-ACCESS read-only
      STATUS current
      ::= { appcLluOperEntry 7 }

appcLluOperOutBoundCompLevel OBJECT-TYPE
      SYNTAX INTEGER {
                      none(1),
                      rle(2),
                      lz9(3),
                      lz10(4),
                      lz12(5)
                     }
      MAX-ACCESS read-only
      STATUS current

      ::= { appcLluOperEntry 8 }

appcLluOperCompRleBeforeLZ OBJECT-TYPE
      SYNTAX INTEGER {
                      no(1),
                      yes(2)
                     }
      MAX-ACCESS read-only
      STATUS current

      ::= { appcLluOperEntry 9 }

appcLluOperAlias OBJECT-TYPE
      SYNTAX DisplayString (SIZE (0..8))
      MAX-ACCESS read-only
      STATUS current

      ::= { appcLluOperEntry 10 }

appcLluOperActiveSessions OBJECT-TYPE
      SYNTAX Gauge32
      MAX-ACCESS read-only
      STATUS current

      ::= { appcLluOperEntry 11 }

appcLuPairAdminTable OBJECT-TYPE
      SYNTAX SEQUENCE OF AppcLuPairAdminEntry
      MAX-ACCESS not-accessible
      STATUS current

      ::= { appcLu 3 }

appcLuPairAdminEntry OBJECT-TYPE
      SYNTAX AppcLuPairAdminEntry
      MAX-ACCESS not-accessible
      STATUS current






      INDEX { appcLuPairAdminLocLuName,
              appcLuPairAdminParLuName }

      ::= { appcLuPairAdminTable 1 }

AppcLuPairAdminEntry     ::= SEQUENCE {

      appcLuPairAdminLocLuName       DisplayString,
      appcLuPairAdminParLuName       DisplayString,
      appcLuPairAdminParLuAlias      DisplayString,
      appcLuPairAdminSessLimit       Integer32,
      appcLuPairAdminSessSec         INTEGER,
      appcLuPairAdminSecAccept       INTEGER,
      appcLuPairAdminLinkObjId       InstancePointer,
      appcLuPairAdminParaSessSup     INTEGER

                     }

appcLuPairAdminLocLuName OBJECT-TYPE
      SYNTAX DisplayString (SIZE (1..17))
      MAX-ACCESS not-accessible
      STATUS current

      ::= { appcLuPairAdminEntry 1 }

appcLuPairAdminParLuName OBJECT-TYPE
      SYNTAX DisplayString (SIZE (1..17))
      MAX-ACCESS not-accessible
      STATUS current






      ::= { appcLuPairAdminEntry 2 }

appcLuPairAdminParLuAlias OBJECT-TYPE
      SYNTAX DisplayString (SIZE (0..8))
      MAX-ACCESS read-only
      STATUS current

      ::= { appcLuPairAdminEntry 3 }

appcLuPairAdminSessLimit OBJECT-TYPE
      SYNTAX Integer32
      MAX-ACCESS read-only
      STATUS current

      ::= { appcLuPairAdminEntry 4 }

appcLuPairAdminSessSec OBJECT-TYPE
      SYNTAX INTEGER {
                      required(1),
                      accepted(2),
                      notAllowed(3)
                     }
      MAX-ACCESS read-only
      STATUS current
      ::= { appcLuPairAdminEntry 5 }


appcLuPairAdminSecAccept OBJECT-TYPE
      SYNTAX INTEGER {





                      none(1),
                      conversation(2),
                      alreadyVerified(3),
                      persistentVerification(4),
                      aVandpV(5)
                     }
      MAX-ACCESS read-only
      STATUS current

      ::= { appcLuPairAdminEntry 6 }

appcLuPairAdminLinkObjId OBJECT-TYPE
      SYNTAX InstancePointer
      MAX-ACCESS read-only
      STATUS current

      ::= { appcLuPairAdminEntry 7 }

appcLuPairAdminParaSessSup OBJECT-TYPE
      SYNTAX INTEGER {
                      no(1),
                      yes(2)
                     }
      MAX-ACCESS read-only
      STATUS current

      ::= { appcLuPairAdminEntry 8 }



appcLuPairOperTable OBJECT-TYPE
      SYNTAX SEQUENCE OF AppcLuPairOperEntry
      MAX-ACCESS not-accessible
      STATUS current
      ::= { appcLu 4 }

appcLuPairOperEntry OBJECT-TYPE
      SYNTAX AppcLuPairOperEntry
      MAX-ACCESS not-accessible
      STATUS current

      INDEX { appcLuPairOperLocLuName,





              appcLuPairOperParLuName  }

      ::= { appcLuPairOperTable 1 }

AppcLuPairOperEntry     ::= SEQUENCE {
    appcLuPairOperLocLuName             DisplayString,
    appcLuPairOperParLuName             DisplayString,
    appcLuPairOperParLuAlias            DisplayString,
    appcLuPairOperSessLimit             Integer32,
    appcLuPairOperSessSec               INTEGER,
    appcLuPairOperSecAccept             INTEGER,
    appcLuPairOperLinkObjId             InstancePointer,
    appcLuPairOperParaSessSup           INTEGER,
    appcLuPairOperParaSessSupLS         INTEGER,
    appcLuPairOperState                 INTEGER
   }

appcLuPairOperLocLuName OBJECT-TYPE
      SYNTAX DisplayString (SIZE (1..17))
      MAX-ACCESS not-accessible
      STATUS current

      ::= { appcLuPairOperEntry 1 }

appcLuPairOperParLuName OBJECT-TYPE
      SYNTAX DisplayString (SIZE (1..17))
      MAX-ACCESS not-accessible
      STATUS current

      ::= { appcLuPairOperEntry 2 }

appcLuPairOperParLuAlias OBJECT-TYPE
      SYNTAX DisplayString (SIZE (0..8))
      MAX-ACCESS read-only
      STATUS current






      ::= { appcLuPairOperEntry 3 }

appcLuPairOperSessLimit OBJECT-TYPE
      SYNTAX Integer32
      MAX-ACCESS read-only
      STATUS current

      ::= { appcLuPairOperEntry 4 }

appcLuPairOperSessSec OBJECT-TYPE
      SYNTAX INTEGER {
                      required(1),
                      accepted(2),
                      notAllowed(3)
                     }
      MAX-ACCESS read-only
      STATUS current

      ::= { appcLuPairOperEntry 5 }

appcLuPairOperSecAccept OBJECT-TYPE
      SYNTAX INTEGER {
                      none(1),
                      conversation(2),
                      alreadyVerified(3),
                      persistentVerification(4),
                      aVandpV(5)
                     }
      MAX-ACCESS read-only





      STATUS current
      ::= { appcLuPairOperEntry 6 }

appcLuPairOperLinkObjId OBJECT-TYPE
      SYNTAX InstancePointer
      MAX-ACCESS read-only
      STATUS current

      ::= { appcLuPairOperEntry 7 }

appcLuPairOperParaSessSup OBJECT-TYPE





      SYNTAX INTEGER {
                      no(1),
                      yes(2)
                     }
      MAX-ACCESS read-only
      STATUS current

      ::= { appcLuPairOperEntry 8 }

appcLuPairOperParaSessSupLS OBJECT-TYPE
      SYNTAX INTEGER {
                      no(1),
                      yes(2)
                     }
      MAX-ACCESS read-only
      STATUS current

      ::= { appcLuPairOperEntry 9 }

appcLuPairOperState OBJECT-TYPE
      SYNTAX INTEGER {
                      inactive (1),
                      active (2)
                     }
      MAX-ACCESS read-only
      STATUS current

      ::= { appcLuPairOperEntry 10 }


appcModeAdminTable OBJECT-TYPE
      SYNTAX SEQUENCE OF AppcModeAdminEntry
      MAX-ACCESS not-accessible
      STATUS current

      ::= { appcLu 5 }

appcModeAdminEntry OBJECT-TYPE
      SYNTAX AppcModeAdminEntry
      MAX-ACCESS not-accessible
      STATUS current
      INDEX { appcModeAdminLocLuName,
              appcModeAdminParLuName,
              appcModeAdminModeName }

      ::= { appcModeAdminTable 1 }

AppcModeAdminEntry     ::= SEQUENCE {
               appcModeAdminLocLuName          DisplayString,
               appcModeAdminParLuName          DisplayString,
               appcModeAdminModeName           DisplayString,
               appcModeAdminCosName            DisplayString,
               appcModeAdminSessEndTpName      DisplayString,
               appcModeAdminMaxSessLimit       Integer32,
               appcModeAdminMinCwinLimit       Integer32,
               appcModeAdminMinClosLimit       Integer32,
               appcModeAdminConWinAutoActLmt   Integer32,
               appcModeAdminRecvPacWinSz       Integer32,
               appcModeAdminSendPacWinSz       Integer32,
               appcModeAdminPrefRecvRuSz       Integer32,
               appcModeAdminPrefSendRuSz       Integer32,
               appcModeAdminRecvRuSzUpBnd      Integer32,
               appcModeAdminSendRuSzUpBnd      Integer32,





               appcModeAdminRecvRuSzLoBnd      Integer32,
               appcModeAdminSendRuSzLoBnd      Integer32,
               appcModeAdminSingSessReinit     INTEGER,
               appcModeAdminCompression        INTEGER,
               appcModeAdminInBoundCompLevel   INTEGER,
               appcModeAdminOutBoundCompLevel  INTEGER,
               appcModeAdminCompRleBeforeLZ    INTEGER,
               appcModeAdminSyncLvl            INTEGER,
               appcModeAdminCrypto             INTEGER

                     }

appcModeAdminLocLuName OBJECT-TYPE
      SYNTAX DisplayString (SIZE (1..17))
      MAX-ACCESS not-accessible
      STATUS current

      ::= { appcModeAdminEntry 1 }

appcModeAdminParLuName OBJECT-TYPE
      SYNTAX DisplayString (SIZE (1..17))
      MAX-ACCESS not-accessible
      STATUS current

      ::= { appcModeAdminEntry 2 }

appcModeAdminModeName OBJECT-TYPE
      SYNTAX DisplayString (SIZE (1..8))
      MAX-ACCESS not-accessible
      STATUS current






      ::= { appcModeAdminEntry 3 }

appcModeAdminCosName OBJECT-TYPE
      SYNTAX DisplayString (SIZE (0..8))
      MAX-ACCESS read-only
      STATUS current

      ::= { appcModeAdminEntry 4 }

appcModeAdminSessEndTpName OBJECT-TYPE
      SYNTAX DisplayString (SIZE (0..64))
      MAX-ACCESS read-only
      STATUS current

      ::= { appcModeAdminEntry 5 }

appcModeAdminMaxSessLimit OBJECT-TYPE
      SYNTAX Integer32
      MAX-ACCESS read-only
      STATUS current

      ::= { appcModeAdminEntry 6 }

appcModeAdminMinCwinLimit OBJECT-TYPE
      SYNTAX Integer32
      MAX-ACCESS read-only
      STATUS current
      ::= { appcModeAdminEntry 7 }

appcModeAdminMinClosLimit OBJECT-TYPE
      SYNTAX Integer32
      MAX-ACCESS read-only
      STATUS current

      ::= { appcModeAdminEntry 8 }

appcModeAdminConWinAutoActLmt OBJECT-TYPE
      SYNTAX Integer32
      MAX-ACCESS read-only
      STATUS current





      ::= { appcModeAdminEntry 9 }

appcModeAdminRecvPacWinSz OBJECT-TYPE
      SYNTAX Integer32
      MAX-ACCESS read-only
      STATUS current

      ::= { appcModeAdminEntry 10 }

appcModeAdminSendPacWinSz OBJECT-TYPE
      SYNTAX Integer32
      MAX-ACCESS read-only
      STATUS current

      ::= { appcModeAdminEntry 11 }

appcModeAdminPrefRecvRuSz OBJECT-TYPE
      SYNTAX Integer32
      MAX-ACCESS read-only
      STATUS current






      ::= { appcModeAdminEntry 12 }

appcModeAdminPrefSendRuSz OBJECT-TYPE
      SYNTAX Integer32
      MAX-ACCESS read-only
      STATUS current

      ::= { appcModeAdminEntry 13 }

appcModeAdminRecvRuSzUpBnd OBJECT-TYPE
      SYNTAX Integer32
      MAX-ACCESS read-only
      STATUS current

      ::= { appcModeAdminEntry 14 }

appcModeAdminSendRuSzUpBnd OBJECT-TYPE
      SYNTAX Integer32
      MAX-ACCESS read-only
      STATUS current

      ::= { appcModeAdminEntry 15 }

appcModeAdminRecvRuSzLoBnd OBJECT-TYPE
      SYNTAX Integer32
      MAX-ACCESS read-only
      STATUS current

      ::= { appcModeAdminEntry 16 }

appcModeAdminSendRuSzLoBnd OBJECT-TYPE
      SYNTAX Integer32
      MAX-ACCESS read-only
      STATUS current

      ::= { appcModeAdminEntry 17 }

appcModeAdminSingSessReinit OBJECT-TYPE
      SYNTAX INTEGER {
                      notApplicable(1),
                      operatorControlled(2),
                      primaryOnly(3),
                      secondaryOnly(4),
                      primaryOrSecondary(5)
                     }
      MAX-ACCESS read-only
      STATUS current
      ::= { appcModeAdminEntry 18 }

appcModeAdminCompression OBJECT-TYPE
      SYNTAX INTEGER {
                      prohibited(1),
                      required(2),
                      negotiable(3)
                     }
      MAX-ACCESS read-only
      STATUS current

      ::= { appcModeAdminEntry 19 }

appcModeAdminInBoundCompLevel OBJECT-TYPE
      SYNTAX INTEGER {
                      none(1),
                      rle(2),
                      lz9(3),
                      lz10(4),
                      lz12(5)
                     }
      MAX-ACCESS read-only
      STATUS current

      ::= { appcModeAdminEntry 20 }

appcModeAdminOutBoundCompLevel OBJECT-TYPE
      SYNTAX INTEGER {
                      none(1),
                      rle(2),
                      lz9(3),
                      lz10(4),
                      lz12(5)
                     }
      MAX-ACCESS read-only
      STATUS current

      ::= { appcModeAdminEntry 21 }

appcModeAdminCompRleBeforeLZ OBJECT-TYPE
      SYNTAX INTEGER {
                      no(1),
                      yes(2)
                     }
      MAX-ACCESS read-only
      STATUS current

      ::= { appcModeAdminEntry 22 }

appcModeAdminSyncLvl OBJECT-TYPE
      SYNTAX INTEGER {
                      none(1),
                      noneConfirm(2),
                      noneConfirmSyncPoint(3)
                     }
      MAX-ACCESS read-only
      STATUS current

      ::= { appcModeAdminEntry 23 }

appcModeAdminCrypto OBJECT-TYPE
      SYNTAX INTEGER {
                      notSupported(1),
                      mandatory(2),
                      selective(3)
                     }





      MAX-ACCESS read-only
      STATUS current

      ::= { appcModeAdminEntry 24 }

appcModeOperTable OBJECT-TYPE
      SYNTAX SEQUENCE OF AppcModeOperEntry
      MAX-ACCESS not-accessible
      STATUS current

      ::= { appcLu 6 }

appcModeOperEntry OBJECT-TYPE
      SYNTAX AppcModeOperEntry
      MAX-ACCESS not-accessible
      STATUS current

      INDEX { appcModeOperLocLuName,
              appcModeOperParLuName,
              appcModeOperModeName }

      ::= { appcModeOperTable 1 }







AppcModeOperEntry     ::= SEQUENCE {

   appcModeOperLocLuName            DisplayString,
   appcModeOperParLuName            DisplayString,
   appcModeOperModeName             DisplayString,
   appcModeOperCosName              DisplayString,
   appcModeOperSessEndTpName        DisplayString,
   appcModeOperSessLimit            Integer32,
   appcModeOperMaxSessLimit         Integer32,
   appcModeOperMinCwinLimit         Integer32,
   appcModeOperMinClosLimit         Integer32,
   appcModeOperConWinAutoActLmt     Integer32,
   appcModeOperRecvPacWinSz         Integer32,
   appcModeOperSendPacWinSz         Integer32,
   appcModeOperPrefRecvRuSz         Integer32,
   appcModeOperPrefSendRuSz         Integer32,
   appcModeOperRecvRuSzUpBnd        Integer32,
   appcModeOperSendRuSzUpBnd        Integer32,
   appcModeOperRecvRuSzLoBnd        Integer32,
   appcModeOperSendRuSzLoBnd        Integer32,
   appcModeOperSingSessReinit       INTEGER,
   appcModeOperCompression          INTEGER,
   appcModeOperInBoundCompLevel     INTEGER,
   appcModeOperOutBoundCompLevel    INTEGER,
   appcModeOperCompRleBeforeLZ      INTEGER,
   appcModeOperSyncLvl              INTEGER,
   appcModeOperCrypto               INTEGER,
   appcModeOperSyncLvlLastStart     INTEGER,
   appcModeOperCryptoLastStart      INTEGER,
   appcModeOperCNOSNeg              INTEGER,
   appcModeOperActCwin              Gauge32,
   appcModeOperActClos              Gauge32,
   appcModeOperPndCwin              Gauge32,
   appcModeOperPndClos              Gauge32,
   appcModeOperPtmCwin              Gauge32,
   appcModeOperPtmClos              Gauge32,
   appcModeOperDrainSelf            INTEGER,
   appcModeOperDrainPart            INTEGER
                     }

appcModeOperLocLuName OBJECT-TYPE
      SYNTAX DisplayString (SIZE (1..17))
      MAX-ACCESS not-accessible
      STATUS current

      ::= { appcModeOperEntry 1 }

appcModeOperParLuName OBJECT-TYPE
      SYNTAX DisplayString (SIZE (1..17))
      MAX-ACCESS not-accessible
      STATUS current

      ::= { appcModeOperEntry 2 }

appcModeOperModeName OBJECT-TYPE
      SYNTAX DisplayString (SIZE (1..8))
      MAX-ACCESS not-accessible
      STATUS current

      ::= { appcModeOperEntry 3 }

appcModeOperCosName OBJECT-TYPE
      SYNTAX DisplayString (SIZE (0..8))
      MAX-ACCESS read-only
      STATUS current

      ::= { appcModeOperEntry 4 }

appcModeOperSessEndTpName OBJECT-TYPE
      SYNTAX DisplayString (SIZE (1..64))
      MAX-ACCESS read-only
      STATUS current

      ::= { appcModeOperEntry 5 }

appcModeOperSessLimit OBJECT-TYPE
      SYNTAX Integer32
      MAX-ACCESS read-only
      STATUS current

      ::= { appcModeOperEntry 6 }

appcModeOperMaxSessLimit OBJECT-TYPE
      SYNTAX Integer32
      MAX-ACCESS read-only
      STATUS current

      ::= { appcModeOperEntry 7 }

appcModeOperMinCwinLimit OBJECT-TYPE
      SYNTAX Integer32
      MAX-ACCESS read-only
      STATUS current

      ::= { appcModeOperEntry 8 }

appcModeOperMinClosLimit OBJECT-TYPE
      SYNTAX Integer32
      MAX-ACCESS read-only
      STATUS current

      ::= { appcModeOperEntry 9 }

appcModeOperConWinAutoActLmt OBJECT-TYPE
      SYNTAX Integer32
      MAX-ACCESS read-only
      STATUS current

      ::= { appcModeOperEntry 10 }

appcModeOperRecvPacWinSz OBJECT-TYPE
      SYNTAX Integer32
      MAX-ACCESS read-only
      STATUS current

      ::= { appcModeOperEntry 11 }

appcModeOperSendPacWinSz OBJECT-TYPE
      SYNTAX Integer32
      MAX-ACCESS read-only





      STATUS current

      ::= { appcModeOperEntry 12 }

appcModeOperPrefRecvRuSz OBJECT-TYPE
      SYNTAX Integer32
      MAX-ACCESS read-only
      STATUS current

      ::= { appcModeOperEntry 13 }

appcModeOperPrefSendRuSz OBJECT-TYPE
      SYNTAX Integer32
      MAX-ACCESS read-only
      STATUS current

      ::= { appcModeOperEntry 14 }






appcModeOperRecvRuSzUpBnd OBJECT-TYPE
      SYNTAX Integer32
      MAX-ACCESS read-only
      STATUS current

      ::= { appcModeOperEntry 15 }

appcModeOperSendRuSzUpBnd OBJECT-TYPE
      SYNTAX Integer32
      MAX-ACCESS read-only
      STATUS current

      ::= { appcModeOperEntry 16 }

appcModeOperRecvRuSzLoBnd OBJECT-TYPE
      SYNTAX Integer32
      MAX-ACCESS read-only
      STATUS current

      ::= { appcModeOperEntry 17 }

appcModeOperSendRuSzLoBnd OBJECT-TYPE
      SYNTAX Integer32
      MAX-ACCESS read-only
      STATUS current

      ::= { appcModeOperEntry 18 }

appcModeOperSingSessReinit OBJECT-TYPE
      SYNTAX INTEGER {
                      notApplicable(1),
                      operatorControlled(2),





                      primaryOnly(3),
                      secondaryOnly(4),
                      primaryOrSecondary(5)
                     }
      MAX-ACCESS read-only
      STATUS current
      ::= { appcModeOperEntry 19 }

appcModeOperCompression OBJECT-TYPE
      SYNTAX INTEGER {
                      prohibited(1),
                      required(2),
                      negotiable(3)
                     }
      MAX-ACCESS read-only





      STATUS current

      ::= { appcModeOperEntry 20 }

appcModeOperInBoundCompLevel OBJECT-TYPE
      SYNTAX INTEGER {
                      none(1),
                      rle(2),
                      lz9(3),
                      lz10(4),
                      lz12(5)
                     }
      MAX-ACCESS read-only
      STATUS current

      ::= { appcModeOperEntry 21 }






appcModeOperOutBoundCompLevel OBJECT-TYPE
      SYNTAX INTEGER {
                      none(1),
                      rle(2),
                      lz9(3),
                      lz10(4),
                      lz12(5)
                     }
      MAX-ACCESS read-only
      STATUS current

      ::= { appcModeOperEntry 22 }

appcModeOperCompRleBeforeLZ OBJECT-TYPE
      SYNTAX INTEGER {
                      no(1),
                      yes(2)
                     }
      MAX-ACCESS read-only
      STATUS current






      ::= { appcModeOperEntry 23 }

appcModeOperSyncLvl OBJECT-TYPE
      SYNTAX INTEGER {
                      none(1),
                      noneConfirm(2),
                      noneConfirmSyncPoint(3)
                     }
      MAX-ACCESS read-only
      STATUS current

      ::= { appcModeOperEntry 24 }

appcModeOperCrypto OBJECT-TYPE
      SYNTAX INTEGER {
                      notSupported(1),
                      mandatory(2),
                      selective(3)
                     }
      MAX-ACCESS read-only
      STATUS current

      ::= { appcModeOperEntry 25 }

appcModeOperSyncLvlLastStart OBJECT-TYPE
      SYNTAX INTEGER {
                      none(1),





                      noneConfirm(2),
                      noneConfirmSyncPoint(3)
                     }
      MAX-ACCESS read-only
      STATUS current

      ::= { appcModeOperEntry 26 }

appcModeOperCryptoLastStart OBJECT-TYPE
      SYNTAX INTEGER {
                      notSupported(1),
                      mandatory(2),
                      selective(3)
                     }
      MAX-ACCESS read-only
      STATUS current

      ::= { appcModeOperEntry 27 }

appcModeOperCNOSNeg OBJECT-TYPE
      SYNTAX INTEGER {
                      no(1),
                      yes(2)
                     }





      MAX-ACCESS read-only
      STATUS current

      ::= { appcModeOperEntry 28 }

appcModeOperActCwin OBJECT-TYPE
      SYNTAX Gauge32
      MAX-ACCESS read-only
      STATUS current

      ::= { appcModeOperEntry 29 }

appcModeOperActClos OBJECT-TYPE
      SYNTAX Gauge32
      MAX-ACCESS read-only
      STATUS current

      ::= { appcModeOperEntry 30 }

appcModeOperPndCwin OBJECT-TYPE
      SYNTAX Gauge32
      MAX-ACCESS read-only
      STATUS current

      ::= { appcModeOperEntry 31 }

appcModeOperPndClos OBJECT-TYPE
      SYNTAX Gauge32
      MAX-ACCESS read-only
      STATUS current

      ::= { appcModeOperEntry 32 }

appcModeOperPtmCwin OBJECT-TYPE





      SYNTAX Gauge32
      MAX-ACCESS read-only
      STATUS current

      ::= { appcModeOperEntry 33 }

appcModeOperPtmClos OBJECT-TYPE
      SYNTAX Gauge32
      MAX-ACCESS read-only
      STATUS current

      ::= { appcModeOperEntry 34 }

appcModeOperDrainSelf OBJECT-TYPE
      SYNTAX INTEGER {
                      no(1),
                      yes(2)
                     }
      MAX-ACCESS read-only
      STATUS current

      ::= { appcModeOperEntry 35 }

appcModeOperDrainPart OBJECT-TYPE
      SYNTAX INTEGER {
                      no(1),
                      yes(2)
                     }
      MAX-ACCESS read-only
      STATUS current

      ::= { appcModeOperEntry 36 }

appcTpAdminTable OBJECT-TYPE
      SYNTAX SEQUENCE OF AppcTpAdminEntry
      MAX-ACCESS not-accessible
      STATUS current

      ::= { appcTp 1 }

appcTpAdminEntry OBJECT-TYPE
      SYNTAX AppcTpAdminEntry
      MAX-ACCESS not-accessible
      STATUS current

      INDEX { appcTpAdminLocLuName,
              appcTpAdminTpName }

      ::= { appcTpAdminTable 1 }

AppcTpAdminEntry     ::= SEQUENCE {
       appcTpAdminLocLuName       DisplayString,
       appcTpAdminTpName          DisplayString,
       appcTpAdminFileSpec        DisplayString,
       appcTpAdminStartParm       DisplayString,
       appcTpAdminTpOperation     INTEGER,
       appcTpAdminInAttachTimeout Integer32,
       appcTpAdminRcvAllocTimeout Integer32,
       appcTpAdminSyncLvl         INTEGER,
       appcTpAdminInstLmt         Integer32,
       appcTpAdminStatus          INTEGER,
       appcTpAdminLongRun         INTEGER,
       appcTpAdminConvType        INTEGER,
       appcTpAdminConvDuplex      INTEGER,
       appcTpAdminConvSecReq      INTEGER,
       appcTpAdminVerPip          INTEGER,
       appcTpAdminPipSubNum       Integer32





                     }

appcTpAdminLocLuName OBJECT-TYPE
      SYNTAX DisplayString (SIZE (1..17))
      MAX-ACCESS not-accessible
      STATUS current

      ::= { appcTpAdminEntry 1 }

appcTpAdminTpName OBJECT-TYPE
      SYNTAX DisplayString (SIZE (1..64))
      MAX-ACCESS not-accessible
      STATUS current

      ::= { appcTpAdminEntry 2 }

appcTpAdminFileSpec OBJECT-TYPE
      SYNTAX DisplayString (SIZE (0..80))
      MAX-ACCESS read-only
      STATUS current

      ::= { appcTpAdminEntry 3 }






appcTpAdminStartParm OBJECT-TYPE
      SYNTAX DisplayString (SIZE (0..128))
      MAX-ACCESS read-only
      STATUS current

      ::= { appcTpAdminEntry 4 }

appcTpAdminTpOperation OBJECT-TYPE
      SYNTAX INTEGER {
                      other(1),
                      queuedOperatorStarted(2),
                      queuedOperatorPreloaded(3),
                      queuedAmStarted(4),
                      nonqueuedAmStarted(5)
                     }
      MAX-ACCESS read-only
      STATUS current

      ::= { appcTpAdminEntry 5 }

appcTpAdminInAttachTimeout OBJECT-TYPE
      SYNTAX Integer32
      MAX-ACCESS read-only
      STATUS current

      ::= { appcTpAdminEntry 6 }

appcTpAdminRcvAllocTimeout OBJECT-TYPE
      SYNTAX Integer32
      MAX-ACCESS read-only
      STATUS current

      ::= { appcTpAdminEntry 7 }

appcTpAdminSyncLvl OBJECT-TYPE
      SYNTAX INTEGER {
                      none(1),
                      confirm(2),
                      noneAndConfirm(3),
                      syncpoint(4),
                      noneAndSyncpoint(5),





                      confirmAndSyncpoint(6),
                      all(7)
                     }
      MAX-ACCESS read-only
      STATUS current

      ::= { appcTpAdminEntry 8 }

appcTpAdminInstLmt OBJECT-TYPE
      SYNTAX Integer32
      MAX-ACCESS read-only
      STATUS current

      ::= { appcTpAdminEntry 9 }

appcTpAdminStatus OBJECT-TYPE
      SYNTAX INTEGER {
                      enabled(1),
                      tempDisabled(2),
                      permDisabled(3)
                     }
      MAX-ACCESS read-only
      STATUS current

      ::= { appcTpAdminEntry 10 }

appcTpAdminLongRun OBJECT-TYPE
      SYNTAX INTEGER {
                      no(1),
                      yes(2)
                     }
      MAX-ACCESS read-only
      STATUS current

      ::= { appcTpAdminEntry 11 }

appcTpAdminConvType OBJECT-TYPE
      SYNTAX INTEGER {
                      basic(1),
                      mapped(2),
                      basicOrMapped(3)
                     }
      MAX-ACCESS read-only
      STATUS current





      ::= { appcTpAdminEntry 12 }

appcTpAdminConvDuplex OBJECT-TYPE
      SYNTAX INTEGER {
                      half(1),
                      full(2),
                      halfOrFull(3)
                     }
      MAX-ACCESS read-only
      STATUS current

      ::= { appcTpAdminEntry 13 }

appcTpAdminConvSecReq OBJECT-TYPE
      SYNTAX INTEGER {
                      no(1),
                      yes(2)
                     }
      MAX-ACCESS read-only
      STATUS current

      ::= { appcTpAdminEntry 14 }

appcTpAdminVerPip OBJECT-TYPE
      SYNTAX INTEGER {
                      no(1),
                      yes(2)
                     }
      MAX-ACCESS read-only
      STATUS current

      ::= { appcTpAdminEntry 15 }

appcTpAdminPipSubNum OBJECT-TYPE
      SYNTAX Integer32
      MAX-ACCESS read-only
      STATUS current

      ::= { appcTpAdminEntry 16 }


appcActSessTable OBJECT-TYPE
      SYNTAX SEQUENCE OF AppcActSessEntry
      MAX-ACCESS not-accessible
      STATUS current

      ::= { appcSession 1 }

appcActSessEntry OBJECT-TYPE
      SYNTAX AppcActSessEntry
      MAX-ACCESS not-accessible
      STATUS current

      INDEX { appcActSessLocLuName,
              appcActSessParLuName,
              appcActSessIndex }

      ::= { appcActSessTable 1 }

AppcActSessEntry     ::= SEQUENCE {
      appcActSessLocLuName            DisplayString,
      appcActSessParLuName            DisplayString,
      appcActSessIndex                Integer32,
      appcActSessPcidCpName           DisplayString,
      appcActSessPcid                 OCTET STRING,
      appcActSessPluIndicator         INTEGER,
      appcActSessModeName             DisplayString,
      appcActSessCosName              DisplayString,
      appcActSessTransPriority        INTEGER,
      appcActSessEnhanceSecSup        INTEGER,
      appcActSessSendPacingType       INTEGER,
      appcActSessSendRpc              Gauge32,
      appcActSessSendNxWndwSize       Gauge32,
      appcActSessRecvPacingType       INTEGER,
      appcActSessRecvRpc              Gauge32,
      appcActSessRecvNxWndwSize       Gauge32,
      appcActSessRscv                 OCTET STRING,
      appcActSessInUse                INTEGER,
      appcActSessMaxSndRuSize         INTEGER,
      appcActSessMaxRcvRuSize         INTEGER,
      appcActSessSndPacingSize        INTEGER,
      appcActSessRcvPacingSize        INTEGER,
      appcActSessOperState            INTEGER,
      appcActSessUpTime               TimeTicks,
      appcActSessRtpNceId             OCTET STRING,
      appcActSessRtpTcid              OCTET STRING,
      appcActSessLinkIndex            InstancePointer
                     }


appcActSessLocLuName OBJECT-TYPE
      SYNTAX DisplayString (SIZE (1..17))
      MAX-ACCESS not-accessible
      STATUS current

      ::= { appcActSessEntry 1 }

appcActSessParLuName OBJECT-TYPE
      SYNTAX DisplayString (SIZE (1..17))
      MAX-ACCESS not-accessible
      STATUS current

      ::= { appcActSessEntry 2 }

appcActSessIndex OBJECT-TYPE
      SYNTAX Integer32
      MAX-ACCESS not-accessible
      STATUS current

      ::= { appcActSessEntry 3 }

appcActSessPcidCpName OBJECT-TYPE
      SYNTAX DisplayString (SIZE (0 | 3..17))
      MAX-ACCESS read-only
      STATUS current





      ::= { appcActSessEntry 4 }

appcActSessPcid OBJECT-TYPE
      SYNTAX OCTET STRING (SIZE (0|8))
      MAX-ACCESS read-only
      STATUS current

      ::= { appcActSessEntry 5 }

appcActSessPluIndicator OBJECT-TYPE
      SYNTAX INTEGER {
                      localLuIsPlu(1),
                      partnerLuIsPlu(2)
                     }
      MAX-ACCESS read-only
      STATUS current

      ::= { appcActSessEntry 6 }

appcActSessModeName OBJECT-TYPE
      SYNTAX DisplayString (SIZE (1..8))
      MAX-ACCESS read-only
      STATUS current

      ::= { appcActSessEntry 7 }

appcActSessCosName OBJECT-TYPE
      SYNTAX DisplayString (SIZE (0..8))
      MAX-ACCESS read-only
      STATUS current

      ::= { appcActSessEntry 8 }

appcActSessTransPriority OBJECT-TYPE
      SYNTAX INTEGER {
                      unknown(1),
                      low(2),
                      medium(3),
                      high(4),
                      network(5)
                     }
      MAX-ACCESS read-only
      STATUS current

      ::= { appcActSessEntry 9 }

appcActSessEnhanceSecSup OBJECT-TYPE
      SYNTAX INTEGER {
                      none(1),
                      level1(2),
                      level2(3)
                     }
      MAX-ACCESS read-only
      STATUS current

      ::= { appcActSessEntry 10 }

appcActSessSendPacingType OBJECT-TYPE
      SYNTAX INTEGER {
                      none(1),





                      fixed(2),
                      adaptive(3)
                     }
      MAX-ACCESS read-only
      STATUS current

      ::= { appcActSessEntry 11 }

appcActSessSendRpc OBJECT-TYPE
      SYNTAX Gauge32
      MAX-ACCESS read-only
      STATUS current

      ::= { appcActSessEntry 12 }

appcActSessSendNxWndwSize OBJECT-TYPE
      SYNTAX Gauge32
      MAX-ACCESS read-only
      STATUS current

      ::= { appcActSessEntry 13 }

appcActSessRecvPacingType OBJECT-TYPE
      SYNTAX INTEGER {
                      none(1),
                      fixed(2),
                      adaptive(3)
                     }
      MAX-ACCESS read-only
      STATUS current

      ::= { appcActSessEntry 14 }

appcActSessRecvRpc OBJECT-TYPE
      SYNTAX Gauge32
      MAX-ACCESS read-only
      STATUS current

      ::= { appcActSessEntry 15 }

appcActSessRecvNxWndwSize OBJECT-TYPE
      SYNTAX Gauge32
      MAX-ACCESS read-only
      STATUS current

      ::= { appcActSessEntry 16 }
appcActSessRscv OBJECT-TYPE
      SYNTAX OCTET STRING (SIZE (0..255))
      MAX-ACCESS read-only
      STATUS current

      ::= { appcActSessEntry 17 }

appcActSessInUse OBJECT-TYPE
      SYNTAX INTEGER {
                      no(1),
                      yes(2)
                     }
      MAX-ACCESS read-only
      STATUS current

      ::= { appcActSessEntry 18 }

appcActSessMaxSndRuSize OBJECT-TYPE
      SYNTAX INTEGER (1..8192)
      MAX-ACCESS read-only
      STATUS current






      ::= { appcActSessEntry 19 }

appcActSessMaxRcvRuSize OBJECT-TYPE
      SYNTAX INTEGER (1..8192)
      MAX-ACCESS read-only
      STATUS current

      ::= { appcActSessEntry 20 }

appcActSessSndPacingSize OBJECT-TYPE
      SYNTAX INTEGER (1..63)
      MAX-ACCESS read-only
      STATUS current

      ::= { appcActSessEntry 21 }

appcActSessRcvPacingSize OBJECT-TYPE
      SYNTAX INTEGER (1..63)
      MAX-ACCESS read-only
      STATUS current

      ::= { appcActSessEntry 22 }

appcActSessOperState OBJECT-TYPE
      SYNTAX INTEGER {
                      unbound (1),
                      pendingBind (2),
                      bound (3),
                      pendingUnbind (4)
                     }
      MAX-ACCESS read-write
      STATUS current

      ::= { appcActSessEntry 23 }

appcActSessUpTime OBJECT-TYPE
      SYNTAX TimeTicks
      MAX-ACCESS read-only
      STATUS current

      ::= { appcActSessEntry 24 }

appcActSessRtpNceId OBJECT-TYPE
      SYNTAX OCTET STRING (SIZE (0..8))
      MAX-ACCESS read-only
      STATUS current





      ::= { appcActSessEntry 25 }

appcActSessRtpTcid OBJECT-TYPE
      SYNTAX OCTET STRING (SIZE (0|8))
      MAX-ACCESS read-only
      STATUS current

      ::= { appcActSessEntry 26 }

appcActSessLinkIndex OBJECT-TYPE
      SYNTAX InstancePointer
      MAX-ACCESS read-only
      STATUS current

      ::= { appcActSessEntry 27 }



appcSessStatsTable OBJECT-TYPE
      SYNTAX SEQUENCE OF AppcSessStatsEntry
      MAX-ACCESS not-accessible
      STATUS current

      ::= { appcSession 2 }

appcSessStatsEntry OBJECT-TYPE
      SYNTAX AppcSessStatsEntry
      MAX-ACCESS not-accessible
      STATUS current






      INDEX { appcSessStatsLocLuName,
              appcSessStatsParLuName,
              appcSessStatsSessIndex }

      ::= { appcSessStatsTable 1 }

AppcSessStatsEntry ::= SEQUENCE {
        appcSessStatsLocLuName           DisplayString,
        appcSessStatsParLuName           DisplayString,
        appcSessStatsSessIndex           Integer32,
        appcSessStatsSentFmdBytes        Counter32,
        appcSessStatsSentNonFmdBytes     Counter32,
        appcSessStatsRcvdFmdBytes        Counter32,
        appcSessStatsRcvdNonFmdBytes     Counter32,
        appcSessStatsSentFmdRus          Counter32,
        appcSessStatsSentNonFmdRus       Counter32,
        appcSessStatsRcvdFmdRus          Counter32,
        appcSessStatsRcvdNonFmdRus       Counter32,
        appcSessStatsCtrUpTime           TimeTicks
                     }

appcSessStatsLocLuName OBJECT-TYPE
      SYNTAX DisplayString (SIZE (1..17))
      MAX-ACCESS not-accessible
      STATUS current

      ::= { appcSessStatsEntry 1 }

appcSessStatsParLuName OBJECT-TYPE
      SYNTAX DisplayString (SIZE (1..17))
      MAX-ACCESS not-accessible
      STATUS current

      ::= { appcSessStatsEntry 2 }

appcSessStatsSessIndex OBJECT-TYPE
      SYNTAX Integer32
      MAX-ACCESS not-accessible
      STATUS current

      ::= { appcSessStatsEntry 3 }

appcSessStatsSentFmdBytes OBJECT-TYPE
      SYNTAX Counter32
      MAX-ACCESS read-only
      STATUS current

      ::= { appcSessStatsEntry 4 }

appcSessStatsSentNonFmdBytes OBJECT-TYPE
      SYNTAX Counter32
      MAX-ACCESS read-only
      STATUS current

      ::= { appcSessStatsEntry 5 }

appcSessStatsRcvdFmdBytes OBJECT-TYPE





      SYNTAX Counter32
      MAX-ACCESS read-only
      STATUS current

      ::= { appcSessStatsEntry 6 }

appcSessStatsRcvdNonFmdBytes OBJECT-TYPE
      SYNTAX Counter32
      MAX-ACCESS read-only
      STATUS current

      ::= { appcSessStatsEntry 7 }

appcSessStatsSentFmdRus OBJECT-TYPE
      SYNTAX Counter32
      MAX-ACCESS read-only
      STATUS current

      ::= { appcSessStatsEntry 8 }

appcSessStatsSentNonFmdRus OBJECT-TYPE
      SYNTAX Counter32
      MAX-ACCESS read-only
      STATUS current

      ::= { appcSessStatsEntry 9 }

appcSessStatsRcvdFmdRus OBJECT-TYPE
      SYNTAX Counter32
      MAX-ACCESS read-only
      STATUS current

      ::= { appcSessStatsEntry 10 }





appcSessStatsRcvdNonFmdRus OBJECT-TYPE
      SYNTAX Counter32
      MAX-ACCESS read-only
      STATUS current

      ::= { appcSessStatsEntry 11 }

appcSessStatsCtrUpTime OBJECT-TYPE
      SYNTAX TimeTicks
      MAX-ACCESS read-only
      STATUS current

      ::= { appcSessStatsEntry 12 }


appcHistSessTable OBJECT-TYPE
      SYNTAX SEQUENCE OF AppcHistSessEntry
      MAX-ACCESS not-accessible
      STATUS current

      ::= { appcSession 3 }

appcHistSessEntry OBJECT-TYPE
      SYNTAX AppcHistSessEntry
      MAX-ACCESS not-accessible
      STATUS current





      INDEX
             { appcHistSessIndex }

      ::= { appcHistSessTable 1 }

AppcHistSessEntry     ::= SEQUENCE {
      appcHistSessIndex           INTEGER,
      appcHistSessTime            DateAndTime,
      appcHistSessType            INTEGER,
      appcHistSessLocLuName       DisplayString,
      appcHistSessParLuName       DisplayString,
      appcHistSessModeName        DisplayString,
      appcHistSessUnbindType      OCTET STRING,
      appcHistSessSenseData       SnaSenseData,
      appcHistSessComponentId     DisplayString,
      appcHistSessDetectModule    DisplayString
                     }


appcHistSessIndex OBJECT-TYPE
      SYNTAX INTEGER (0..2147483647)
      MAX-ACCESS not-accessible
      STATUS current

      ::=  { appcHistSessEntry 1 }

appcHistSessTime OBJECT-TYPE
      SYNTAX DateAndTime
      MAX-ACCESS read-only
      STATUS current

      ::=  { appcHistSessEntry 2 }

appcHistSessType OBJECT-TYPE
      SYNTAX INTEGER {
                      recvNegBindRsp(1),
                      sendNegBindRsp(2),
                      sessActRejected(3),
                      unbindSent(4),
                      unbindReceived(5)
                     }





      MAX-ACCESS read-only
      STATUS current

      ::=  { appcHistSessEntry 3 }

appcHistSessLocLuName OBJECT-TYPE
      SYNTAX DisplayString (SIZE (1..17))
      MAX-ACCESS read-only
      STATUS current

      ::=  { appcHistSessEntry 4 }

appcHistSessParLuName OBJECT-TYPE
      SYNTAX DisplayString (SIZE (3..17))
      MAX-ACCESS read-only
      STATUS current

      ::=  { appcHistSessEntry 5 }

appcHistSessModeName OBJECT-TYPE
      SYNTAX DisplayString (SIZE (1..8))
      MAX-ACCESS read-only
      STATUS current





      ::=  { appcHistSessEntry 6 }

appcHistSessUnbindType OBJECT-TYPE
      SYNTAX OCTET STRING (SIZE (1))
      MAX-ACCESS read-only
      STATUS current

      ::=  { appcHistSessEntry 7 }

appcHistSessSenseData OBJECT-TYPE
      SYNTAX SnaSenseData
      MAX-ACCESS read-only
      STATUS current

      ::=  { appcHistSessEntry 8 }

appcHistSessComponentId OBJECT-TYPE
      SYNTAX DisplayString (SIZE (0..32))
      MAX-ACCESS read-only
      STATUS current

      ::=  { appcHistSessEntry 9 }

appcHistSessDetectModule OBJECT-TYPE
      SYNTAX DisplayString (SIZE (0..32))
      MAX-ACCESS read-only
      STATUS current

      ::=  { appcHistSessEntry 10 }







appcSessRtpTable OBJECT-TYPE
      SYNTAX SEQUENCE OF AppcSessRtpEntry
      MAX-ACCESS not-accessible
      STATUS current

      ::= { appcSession 4 }

appcSessRtpEntry OBJECT-TYPE
      SYNTAX AppcSessRtpEntry
      MAX-ACCESS not-accessible
      STATUS current

      INDEX { appcSessRtpNceId,
              appcSessRtpTcid }

      ::= { appcSessRtpTable 1 }

AppcSessRtpEntry ::= SEQUENCE {
      appcSessRtpNceId              OCTET STRING,
      appcSessRtpTcid               OCTET STRING,
      appcSessRtpSessions           Gauge32
                     }

appcSessRtpNceId OBJECT-TYPE
      SYNTAX OCTET STRING (SIZE (1..8))
      MAX-ACCESS not-accessible
      STATUS current

      ::= { appcSessRtpEntry 1 }

appcSessRtpTcid OBJECT-TYPE
      SYNTAX OCTET STRING (SIZE (8))
      MAX-ACCESS not-accessible
      STATUS current

      ::= { appcSessRtpEntry 2 }





appcSessRtpSessions OBJECT-TYPE
      SYNTAX Gauge32
      MAX-ACCESS read-only
      STATUS current

      ::= { appcSessRtpEntry 3 }



appcActiveConvTable OBJECT-TYPE
      SYNTAX SEQUENCE OF AppcActiveConvEntry
      MAX-ACCESS not-accessible
      STATUS current

      ::= { appcConversation 1 }

appcActiveConvEntry OBJECT-TYPE
      SYNTAX AppcActiveConvEntry
      MAX-ACCESS not-accessible
      STATUS current

      INDEX { appcActiveConvLocLuName,
              appcActiveConvParLuName,
              appcActiveConvSessIndex }

      ::= { appcActiveConvTable 1}

AppcActiveConvEntry     ::= SEQUENCE {
           appcActiveConvLocLuName           DisplayString,
           appcActiveConvParLuName           DisplayString,
           appcActiveConvSessIndex           Integer32,
           appcActiveConvId                  OCTET STRING,
           appcActiveConvState               INTEGER,
           appcActiveConvType                INTEGER,





           appcActiveConvCorrelator          OCTET STRING,
           appcActiveConvSyncLvl             INTEGER,
           appcActiveConvSource              INTEGER,
           appcActiveConvDuplex              INTEGER,
           appcActiveConvUpTime              TimeTicks,
           appcActiveConvSendBytes           Counter32,
           appcActiveConvRcvBytes            Counter32,
           appcActiveConvUserid              DisplayString,
           appcActiveConvPcidNauName         DisplayString,
           appcActiveConvPcid                OCTET STRING,
           appcActiveConvModeName            DisplayString,
           appcActiveConvLuwIdName           DisplayString,
           appcActiveConvLuwIdInstance       OCTET STRING,
           appcActiveConvLuwIdSequence       OCTET STRING,
           appcActiveConvTpName              DisplayString
                     }

appcActiveConvLocLuName OBJECT-TYPE
      SYNTAX DisplayString (SIZE (1..17))
      MAX-ACCESS not-accessible
      STATUS current

      ::= { appcActiveConvEntry 1 }

appcActiveConvParLuName OBJECT-TYPE
      SYNTAX DisplayString (SIZE (1..17))
      MAX-ACCESS not-accessible
      STATUS current

      ::= { appcActiveConvEntry 2 }





appcActiveConvSessIndex OBJECT-TYPE
      SYNTAX Integer32
      MAX-ACCESS not-accessible
      STATUS current

      ::= { appcActiveConvEntry 3 }

appcActiveConvId OBJECT-TYPE
      SYNTAX OCTET STRING (SIZE (4))
      MAX-ACCESS read-only
      STATUS current

      ::= { appcActiveConvEntry 4 }

appcActiveConvState OBJECT-TYPE
      SYNTAX INTEGER {
                      reset(1),
                      send(2),
                      receive(3),
                      confirm(4),
                      confirmSend(5),
                      confirmDealloc(6),
                      pendingDeallocate(7),
                      pendingPost(8),
                      sendReceive(9),
                      sendOnly(10),
                      receiveOnly(11),
                      deferReceive(12),
                      deferDeallocate(13),
                      syncpoint(14),
                      syncpointSend(15),
                      syncpointDeallocate(16),
                      backoutRequired(17)
                     }

      MAX-ACCESS read-only
      STATUS current

      ::= { appcActiveConvEntry 5 }

appcActiveConvType OBJECT-TYPE
      SYNTAX INTEGER {
                      basic(1),
                      mapped(2)
                     }
      MAX-ACCESS read-only
      STATUS current


      ::= { appcActiveConvEntry 6 }

appcActiveConvCorrelator OBJECT-TYPE
      SYNTAX OCTET STRING (SIZE (0..8))
      MAX-ACCESS read-only
      STATUS current

      ::= { appcActiveConvEntry 7 }

appcActiveConvSyncLvl OBJECT-TYPE
      SYNTAX INTEGER {
                      none(1),
                      confirm(2),
                      syncpt(3)
                     }
      MAX-ACCESS read-only
      STATUS current

      ::= { appcActiveConvEntry 8 }

appcActiveConvSource OBJECT-TYPE
      SYNTAX INTEGER {
                      localLu(1),
                      partnerLu(2)
                     }





      MAX-ACCESS read-only
      STATUS current

      ::= { appcActiveConvEntry 9 }

appcActiveConvDuplex OBJECT-TYPE
      SYNTAX INTEGER {
                      half(1),
                      full(2)
                     }
      MAX-ACCESS read-only
      STATUS current

      ::= { appcActiveConvEntry 10 }

appcActiveConvUpTime OBJECT-TYPE
      SYNTAX TimeTicks
      MAX-ACCESS read-only
      STATUS current

      ::= { appcActiveConvEntry 11 }





appcActiveConvSendBytes OBJECT-TYPE
      SYNTAX Counter32
      MAX-ACCESS read-only
      STATUS current

      ::= { appcActiveConvEntry 12 }

appcActiveConvRcvBytes OBJECT-TYPE
      SYNTAX Counter32
      MAX-ACCESS read-only
      STATUS current

      ::= { appcActiveConvEntry 13 }

appcActiveConvUserid OBJECT-TYPE
      SYNTAX DisplayString (SIZE (0..10))
      MAX-ACCESS read-only
      STATUS current

      ::= { appcActiveConvEntry 14 }

appcActiveConvPcidNauName OBJECT-TYPE
      SYNTAX DisplayString (SIZE (0 | 3..17))
      MAX-ACCESS read-only
      STATUS current

      ::= { appcActiveConvEntry 15 }

appcActiveConvPcid OBJECT-TYPE
      SYNTAX OCTET STRING (SIZE (0|8))
      MAX-ACCESS read-only
      STATUS current

      ::= { appcActiveConvEntry 16 }

appcActiveConvModeName OBJECT-TYPE
      SYNTAX DisplayString (SIZE (1..8))
      MAX-ACCESS read-only
      STATUS current

      ::= { appcActiveConvEntry 17 }

appcActiveConvLuwIdName OBJECT-TYPE
      SYNTAX DisplayString (SIZE (1..17))
      MAX-ACCESS read-only
      STATUS current

      ::= { appcActiveConvEntry 18 }

appcActiveConvLuwIdInstance OBJECT-TYPE
      SYNTAX OCTET STRING (SIZE (0..6))
      MAX-ACCESS read-only
      STATUS current

      ::= { appcActiveConvEntry 19 }






appcActiveConvLuwIdSequence OBJECT-TYPE
      SYNTAX OCTET STRING (SIZE (0..2))
      MAX-ACCESS read-only
      STATUS current

      ::= { appcActiveConvEntry 20 }

appcActiveConvTpName OBJECT-TYPE
      SYNTAX DisplayString (SIZE (0..64))
      MAX-ACCESS read-only
      STATUS current

      ::= { appcActiveConvEntry 21 }


appcHistConvTable OBJECT-TYPE
      SYNTAX SEQUENCE OF AppcHistConvEntry
      MAX-ACCESS not-accessible
      STATUS current

      ::= { appcConversation 2 }

appcHistConvEntry OBJECT-TYPE
      SYNTAX AppcHistConvEntry
      MAX-ACCESS not-accessible
      STATUS current

      INDEX
             { appcHistConvIndex  }

      ::= { appcHistConvTable 1}

AppcHistConvEntry     ::= SEQUENCE {
      appcHistConvIndex           Integer32,
      appcHistConvEndTime         DateAndTime,
      appcHistConvLocLuName       DisplayString,
      appcHistConvParLuName       DisplayString,
      appcHistConvTpName          DisplayString,
      appcHistConvPcidNauName     DisplayString,
      appcHistConvPcid            OCTET STRING,
      appcHistConvSenseData       SnaSenseData,
      appcHistConvLogData         OCTET STRING,
      appcHistConvEndedBy         INTEGER
                     }

appcHistConvIndex OBJECT-TYPE
      SYNTAX Integer32
      MAX-ACCESS not-accessible
      STATUS current

      ::= { appcHistConvEntry 1 }

appcHistConvEndTime OBJECT-TYPE





      SYNTAX DateAndTime
      MAX-ACCESS read-only
      STATUS current

      ::= { appcHistConvEntry 2 }

appcHistConvLocLuName OBJECT-TYPE
      SYNTAX DisplayString (SIZE (1..17))
      MAX-ACCESS read-only
      STATUS current

      ::= { appcHistConvEntry 3 }

appcHistConvParLuName OBJECT-TYPE
      SYNTAX DisplayString (SIZE (1..17))
      MAX-ACCESS read-only
      STATUS current

      ::= { appcHistConvEntry 4 }

appcHistConvTpName OBJECT-TYPE
      SYNTAX DisplayString (SIZE (0..64))
      MAX-ACCESS read-only
      STATUS current

      ::= { appcHistConvEntry 5 }

appcHistConvPcidNauName OBJECT-TYPE
      SYNTAX DisplayString (SIZE (0 | 3..17))
      MAX-ACCESS read-only
      STATUS current

      ::= { appcHistConvEntry 6 }

appcHistConvPcid OBJECT-TYPE
      SYNTAX OCTET STRING (SIZE (0|8))
      MAX-ACCESS read-only
      STATUS current

      ::= { appcHistConvEntry 7 }

appcHistConvSenseData OBJECT-TYPE
      SYNTAX SnaSenseData
      MAX-ACCESS read-only
      STATUS current

      ::= { appcHistConvEntry 8 }






appcHistConvLogData OBJECT-TYPE
      SYNTAX OCTET STRING (SIZE (0..32))
      MAX-ACCESS read-only
      STATUS current

      ::= { appcHistConvEntry 9 }

appcHistConvEndedBy OBJECT-TYPE
      SYNTAX INTEGER {
                      localLu(1),
                      partnerLu(2)
                     }
      MAX-ACCESS read-only
      STATUS current

      ::= { appcHistConvEntry 10 }

appcCpicAdminTable OBJECT-TYPE
      SYNTAX SEQUENCE OF AppcCpicAdminEntry
      MAX-ACCESS not-accessible
      STATUS current

      ::= { appcCPIC 1 }

appcCpicAdminEntry OBJECT-TYPE
      SYNTAX AppcCpicAdminEntry
      MAX-ACCESS not-accessible
      STATUS current






      INDEX { appcCpicAdminLocLuName,
              appcCpicAdminSymbDestName }

      ::= { appcCpicAdminTable 1 }

AppcCpicAdminEntry ::= SEQUENCE {
          appcCpicAdminLocLuName          DisplayString,
          appcCpicAdminSymbDestName       DisplayString,
          appcCpicAdminParLuAlias         DisplayString,
          appcCpicAdminParLuName          DisplayString,
          appcCpicAdminModeName           DisplayString,
          appcCpicAdminTpNameType         INTEGER,
          appcCpicAdminTpName             DisplayString,
          appcCpicAdminUserid             DisplayString,
          appcCpicAdminSecurity           INTEGER
                     }

appcCpicAdminLocLuName OBJECT-TYPE
      SYNTAX DisplayString (SIZE (1..17))
      MAX-ACCESS not-accessible
      STATUS current

      ::= { appcCpicAdminEntry 1 }

appcCpicAdminSymbDestName OBJECT-TYPE
      SYNTAX DisplayString (SIZE (1..8))
      MAX-ACCESS not-accessible
      STATUS current

      ::= { appcCpicAdminEntry 2 }

appcCpicAdminParLuAlias OBJECT-TYPE
      SYNTAX DisplayString (SIZE (0..8))
      MAX-ACCESS read-only
      STATUS current

      ::= { appcCpicAdminEntry 3 }


appcCpicAdminParLuName OBJECT-TYPE
      SYNTAX DisplayString (SIZE (1..17))
      MAX-ACCESS read-only
      STATUS current

      ::= { appcCpicAdminEntry 4 }


appcCpicAdminModeName OBJECT-TYPE
      SYNTAX DisplayString (SIZE (1..8))
      MAX-ACCESS read-only
      STATUS current

      ::= { appcCpicAdminEntry 5 }


appcCpicAdminTpNameType OBJECT-TYPE
      SYNTAX INTEGER {
                      normal(1),
                      snaServiceTp(2)
                     }
      MAX-ACCESS read-only
      STATUS current

      ::= { appcCpicAdminEntry 6 }

appcCpicAdminTpName OBJECT-TYPE
      SYNTAX DisplayString (SIZE (1..64))





      MAX-ACCESS read-only
      STATUS current

      ::= { appcCpicAdminEntry 7 }

appcCpicAdminUserid OBJECT-TYPE
      SYNTAX DisplayString (SIZE (0..10))
      MAX-ACCESS read-only
      STATUS current

      ::= { appcCpicAdminEntry 8 }

appcCpicAdminSecurity OBJECT-TYPE
      SYNTAX INTEGER {
                      none(1),
                      same(2),
                      pgm(3),
                      pgmStrong(4),
                      distributed(5),
                      mutual(6)
                     }
      MAX-ACCESS read-only
      STATUS current

      ::= { appcCpicAdminEntry 9 }



appcCpicOperTable OBJECT-TYPE
      SYNTAX SEQUENCE OF AppcCpicOperEntry
      MAX-ACCESS not-accessible
      STATUS current

      ::= { appcCPIC 2 }

appcCpicOperEntry OBJECT-TYPE
      SYNTAX AppcCpicOperEntry
      MAX-ACCESS not-accessible
      STATUS current

      INDEX { appcCpicOperLocLuName,
              appcCpicOperSymbDestName }

      ::= { appcCpicOperTable 1 }







AppcCpicOperEntry ::= SEQUENCE {
          appcCpicOperLocLuName          DisplayString,
          appcCpicOperSymbDestName       DisplayString,
          appcCpicOperParLuAlias         DisplayString,
          appcCpicOperParLuName          DisplayString,
          appcCpicOperModeName           DisplayString,
          appcCpicOperTpNameType         INTEGER,
          appcCpicOperTpName             DisplayString,
          appcCpicOperUserid             DisplayString,
          appcCpicOperSecurity           INTEGER
                     }

appcCpicOperLocLuName OBJECT-TYPE
      SYNTAX DisplayString (SIZE (1..17))
      MAX-ACCESS not-accessible
      STATUS current

      ::= { appcCpicOperEntry 1 }

appcCpicOperSymbDestName OBJECT-TYPE
      SYNTAX DisplayString (SIZE (1..8))
      MAX-ACCESS not-accessible
      STATUS current

      ::= { appcCpicOperEntry 2 }

appcCpicOperParLuAlias OBJECT-TYPE
      SYNTAX DisplayString (SIZE (0..8))
      MAX-ACCESS read-only
      STATUS current

      ::= { appcCpicOperEntry 3 }

appcCpicOperParLuName OBJECT-TYPE





      SYNTAX DisplayString (SIZE (1..17))
      MAX-ACCESS read-only
      STATUS current

      ::= { appcCpicOperEntry 4 }


appcCpicOperModeName OBJECT-TYPE
      SYNTAX DisplayString (SIZE (1..8))
      MAX-ACCESS read-only
      STATUS current

      ::= { appcCpicOperEntry 5 }


appcCpicOperTpNameType OBJECT-TYPE
      SYNTAX INTEGER {
                      normal(1),
                      snaServiceTp(2)
                     }
      MAX-ACCESS read-only
      STATUS current

      ::= { appcCpicOperEntry 6 }

appcCpicOperTpName OBJECT-TYPE
      SYNTAX DisplayString (SIZE (1..64))
      MAX-ACCESS read-only
      STATUS current

      ::= { appcCpicOperEntry 7 }

appcCpicOperUserid OBJECT-TYPE
      SYNTAX DisplayString (SIZE (0..10))
      MAX-ACCESS read-only
      STATUS current

      ::= { appcCpicOperEntry 8 }

appcCpicOperSecurity OBJECT-TYPE
      SYNTAX INTEGER {
                      none(1),
                      same(2),
                      pgm(3),
                      pgmStrong(4),
                      distributed(5),
                      mutual(6)
                     }
      MAX-ACCESS read-only
      STATUS current

      ::= { appcCpicOperEntry 9 }



appcConformance       OBJECT IDENTIFIER ::= {appcMIB 2 }

appcCompliances       OBJECT IDENTIFIER ::= {appcConformance 1 }
appcGroups            OBJECT IDENTIFIER ::= {appcConformance 2 }

appcCompliance  MODULE-COMPLIANCE
      STATUS current

      MODULE  -- this module

      MANDATORY-GROUPS  {
                        appcGlobalConfGroup,
                        appcLluConfGroup,
                        appcParLuConfGroup,
                        appcModeConfGroup,
                        appcTpConfGroup,
                        appcSessionConfGroup
                }

      GROUP  appcControlConfGroup






      GROUP  appcCnosConfGroup

      GROUP  appcCpicConfGroup


      GROUP  appcConversationConfGroup

        OBJECT appcActSessOperState
        MIN-ACCESS read-only

      ::= {appcCompliances 1 }

appcGlobalConfGroup OBJECT-GROUP
      OBJECTS  {
                appcUpTime,
                appcDefaultModeName,
                appcDefaultLuName,
                appcDefaultImplInbndPlu,
                appcDefaultMaxMcLlSndSize,
                appcDefaultFileSpec,
                appcDefaultTpOperation,
                appcDefaultTpConvSecRqd,
                appcLocalCpName,
                appcActiveSessions,
                appcActiveHprSessions
                }
      STATUS current

      ::= { appcGroups 1 }






appcLluConfGroup OBJECT-GROUP
      OBJECTS  {
                appcLluAdminDepType,
                appcLluAdminLocalAddress,
                appcLluAdminSessLimit,
                appcLluAdminBindRspMayQ,
                appcLluAdminCompression,
                appcLluAdminInBoundCompLevel,
                appcLluAdminOutBoundCompLevel,
                appcLluAdminCompRleBeforeLZ,
                appcLluAdminAlias,

                appcLluOperDepType,
                appcLluOperLocalAddress,
                appcLluOperSessLimit,
                appcLluOperBindRspMayQ,
                appcLluOperCompression,
                appcLluOperInBoundCompLevel,
                appcLluOperOutBoundCompLevel,
                appcLluOperCompRleBeforeLZ,
                appcLluOperAlias,
                appcLluOperActiveSessions
                }
      STATUS current

      ::= { appcGroups 2 }

appcParLuConfGroup OBJECT-GROUP
      OBJECTS  {
                appcLuPairAdminParLuAlias,
                appcLuPairAdminSessLimit,
                appcLuPairAdminSessSec,
                appcLuPairAdminSecAccept,
                appcLuPairAdminLinkObjId,
                appcLuPairAdminParaSessSup,

                appcLuPairOperParLuAlias,
                appcLuPairOperSessLimit,
                appcLuPairOperSessSec,
                appcLuPairOperSecAccept,
                appcLuPairOperLinkObjId,
                appcLuPairOperParaSessSup,
                appcLuPairOperParaSessSupLS,
                appcLuPairOperState
                }





      STATUS current

      ::= { appcGroups 3 }

appcModeConfGroup OBJECT-GROUP
      OBJECTS  {
               appcModeAdminCosName,
               appcModeAdminSessEndTpName,
               appcModeAdminMaxSessLimit,
               appcModeAdminMinCwinLimit,
               appcModeAdminMinClosLimit,
               appcModeAdminConWinAutoActLmt,
               appcModeAdminRecvPacWinSz,
               appcModeAdminSendPacWinSz,
               appcModeAdminPrefRecvRuSz,

               appcModeAdminPrefSendRuSz,
               appcModeAdminRecvRuSzUpBnd,
               appcModeAdminSendRuSzUpBnd,
               appcModeAdminRecvRuSzLoBnd,
               appcModeAdminSendRuSzLoBnd,
               appcModeAdminSingSessReinit,
               appcModeAdminCompression,
               appcModeAdminInBoundCompLevel,
               appcModeAdminOutBoundCompLevel,
               appcModeAdminCompRleBeforeLZ,
               appcModeAdminSyncLvl,
               appcModeAdminCrypto,

               appcModeOperCosName,
               appcModeOperSessEndTpName,
               appcModeOperSessLimit,
               appcModeOperMaxSessLimit,
               appcModeOperMinCwinLimit,
               appcModeOperMinClosLimit,
               appcModeOperConWinAutoActLmt,
               appcModeOperRecvPacWinSz,
               appcModeOperSendPacWinSz,
               appcModeOperPrefRecvRuSz,
               appcModeOperPrefSendRuSz,
               appcModeOperRecvRuSzUpBnd,
               appcModeOperSendRuSzUpBnd,
               appcModeOperRecvRuSzLoBnd,
               appcModeOperSendRuSzLoBnd,
               appcModeOperSingSessReinit,





               appcModeOperCompression,
               appcModeOperInBoundCompLevel,
               appcModeOperOutBoundCompLevel,
               appcModeOperCompRleBeforeLZ,
               appcModeOperSyncLvl,
               appcModeOperCrypto,
               appcModeOperSyncLvlLastStart,
               appcModeOperCryptoLastStart,
               appcModeOperCNOSNeg,
               appcModeOperActCwin,
               appcModeOperActClos,
               appcModeOperPndCwin,
               appcModeOperPndClos,
               appcModeOperPtmCwin,
               appcModeOperPtmClos,
               appcModeOperDrainSelf,
               appcModeOperDrainPart
                }
      STATUS current

      ::= { appcGroups 4 }

appcTpConfGroup OBJECT-GROUP
      OBJECTS  {
                appcTpAdminFileSpec,
                appcTpAdminStartParm,
                appcTpAdminTpOperation,
                appcTpAdminInAttachTimeout,
                appcTpAdminRcvAllocTimeout,
                appcTpAdminSyncLvl,
                appcTpAdminInstLmt,
                appcTpAdminStatus,
                appcTpAdminLongRun,
                appcTpAdminConvType,
                appcTpAdminConvDuplex,
                appcTpAdminConvSecReq,
                appcTpAdminVerPip,
                appcTpAdminPipSubNum
                }
      STATUS current

      ::= { appcGroups 5 }





appcSessionConfGroup OBJECT-GROUP
      OBJECTS  {
                appcActSessPcidCpName,
                appcActSessPcid,
                appcActSessPluIndicator,
                appcActSessModeName,
                appcActSessCosName,
                appcActSessTransPriority,
                appcActSessEnhanceSecSup,
                appcActSessSendPacingType,
                appcActSessSendRpc,
                appcActSessSendNxWndwSize,
                appcActSessRecvPacingType,
                appcActSessRecvRpc,
                appcActSessRecvNxWndwSize,
                appcActSessRscv,
                appcActSessInUse,
                appcActSessMaxSndRuSize,
                appcActSessMaxRcvRuSize,
                appcActSessSndPacingSize,
                appcActSessRcvPacingSize,
                appcActSessOperState,
                appcActSessUpTime,
                appcActSessRtpNceId,
                appcActSessRtpTcid,
                appcActSessLinkIndex,

                appcSessStatsSentFmdBytes,
                appcSessStatsSentNonFmdBytes,
                appcSessStatsRcvdFmdBytes,
                appcSessStatsRcvdNonFmdBytes,
                appcSessStatsSentFmdRus,
                appcSessStatsSentNonFmdRus,
                appcSessStatsRcvdFmdRus,
                appcSessStatsRcvdNonFmdRus,
                appcSessStatsCtrUpTime,

                appcHistSessTime,
                appcHistSessType,
                appcHistSessLocLuName,
                appcHistSessParLuName,
                appcHistSessModeName,
                appcHistSessUnbindType,
                appcHistSessSenseData,
                appcHistSessComponentId,
                appcHistSessDetectModule,

                appcSessRtpSessions





                }
      STATUS current

      ::= { appcGroups 6 }

appcControlConfGroup OBJECT-GROUP
      OBJECTS  {
                appcCntrlAdminStat,
                appcCntrlAdminRscv,
                appcCntrlAdminTrace,
                appcCntrlAdminTraceParm,
                appcCntrlOperStat,
                appcCntrlOperStatTime,
                appcCntrlOperRscv,
                appcCntrlOperRscvTime,
                appcCntrlOperTrace,
                appcCntrlOperTraceTime,
                appcCntrlOperTraceParm

                }
      STATUS current

      ::= { appcGroups 7 }

appcCnosConfGroup OBJECT-GROUP
      OBJECTS  {
                appcCnosCommand,
                appcCnosMaxSessLimit,
                appcCnosMinCwinLimit,
                appcCnosMinClosLimit,
                appcCnosDrainSelf,
                appcCnosDrainPart,
                appcCnosResponsible,
                appcCnosForce,
                appcCnosTargetLocLuName,
                appcCnosTargetParLuName,
                appcCnosTargetModeName
                }
      STATUS current





      ::= { appcGroups 8 }

appcCpicConfGroup OBJECT-GROUP
      OBJECTS  {
                appcCpicAdminParLuAlias,
                appcCpicAdminParLuName,
                appcCpicAdminModeName,
                appcCpicAdminTpNameType,
                appcCpicAdminTpName,
                appcCpicAdminUserid,
                appcCpicAdminSecurity,
                appcCpicOperParLuAlias,
                appcCpicOperParLuName,
                appcCpicOperModeName,
                appcCpicOperTpNameType,
                appcCpicOperTpName,
                appcCpicOperUserid,
                appcCpicOperSecurity
                }
      STATUS current

      ::= { appcGroups 9 }

appcConversationConfGroup OBJECT-GROUP
      OBJECTS  {
                appcActiveConvId,
                appcActiveConvState,
                appcActiveConvType,
                appcActiveConvCorrelator,
                appcActiveConvSyncLvl,
                appcActiveConvSource,
                appcActiveConvDuplex,
                appcActiveConvUpTime,
                appcActiveConvSendBytes,
                appcActiveConvRcvBytes,
                appcActiveConvUserid,
                appcActiveConvPcidNauName,
                appcActiveConvPcid,
                appcActiveConvModeName,
                appcActiveConvLuwIdName,
                appcActiveConvLuwIdInstance,
                appcActiveConvLuwIdSequence,
                appcActiveConvTpName,

                appcHistConvEndTime,





                appcHistConvLocLuName,
                appcHistConvParLuName,
                appcHistConvTpName,
                appcHistConvPcidNauName,
                appcHistConvPcid,
                appcHistConvSenseData,
                appcHistConvLogData,
                appcHistConvEndedBy
                }
      STATUS current

      ::= { appcGroups 10 }


END

DISMAN-SCRIPT-MIB DEFINITIONS ::= BEGIN

   IMPORTS
       MODULE-IDENTITY, OBJECT-TYPE, NOTIFICATION-TYPE,
       Integer32, Unsigned32, mib-2
           FROM SNMPv2-SMI

       RowStatus, TimeInterval, DateAndTime, StorageType, DisplayString
           FROM SNMPv2-TC

       MODULE-COMPLIANCE, OBJECT-GROUP, NOTIFICATION-GROUP
           FROM SNMPv2-CONF

       SnmpAdminString
           FROM SNMP-FRAMEWORK-MIB;

   scriptMIB MODULE-IDENTITY
       LAST-UPDATED "200108210000Z"
       ORGANIZATION "IETF Distributed Management Working Group"





       ::= { mib-2 64 }


   smObjects       OBJECT IDENTIFIER ::= { scriptMIB 1 }
   smNotifications OBJECT IDENTIFIER ::= { scriptMIB 2 }
   smConformance   OBJECT IDENTIFIER ::= { scriptMIB 3 }


   smLangTable OBJECT-TYPE
       SYNTAX      SEQUENCE OF SmLangEntry
       MAX-ACCESS  not-accessible
       STATUS      current
       ::= { smObjects 1 }

   smLangEntry OBJECT-TYPE
       SYNTAX      SmLangEntry
       MAX-ACCESS  not-accessible
       STATUS      current
       INDEX { smLangIndex }
       ::= { smLangTable 1 }

   SmLangEntry ::= SEQUENCE {
       smLangIndex         Integer32,
       smLangLanguage      OBJECT IDENTIFIER,
       smLangVersion       SnmpAdminString,
       smLangVendor        OBJECT IDENTIFIER,
       smLangRevision      SnmpAdminString,
       smLangDescr         SnmpAdminString
   }

   smLangIndex OBJECT-TYPE





       SYNTAX      Integer32 (1..2147483647)
       MAX-ACCESS  not-accessible
       STATUS      current
       ::= { smLangEntry 1 }

   smLangLanguage OBJECT-TYPE
       SYNTAX      OBJECT IDENTIFIER
       MAX-ACCESS  read-only
       STATUS      current
       ::= { smLangEntry 2 }

   smLangVersion OBJECT-TYPE
       SYNTAX      SnmpAdminString (SIZE (0..32))
       MAX-ACCESS  read-only
       STATUS      current
       ::= { smLangEntry 3 }

   smLangVendor OBJECT-TYPE
       SYNTAX      OBJECT IDENTIFIER
       MAX-ACCESS  read-only
       STATUS      current





       ::= { smLangEntry 4 }

   smLangRevision OBJECT-TYPE
       SYNTAX      SnmpAdminString (SIZE (0..32))
       MAX-ACCESS  read-only
       STATUS      current
       ::= { smLangEntry 5 }

   smLangDescr OBJECT-TYPE
       SYNTAX      SnmpAdminString
       MAX-ACCESS  read-only
       STATUS      current
       ::= { smLangEntry 6 }


   smExtsnTable OBJECT-TYPE
       SYNTAX      SEQUENCE OF SmExtsnEntry
       MAX-ACCESS  not-accessible
       STATUS      current
       ::= { smObjects 2 }

   smExtsnEntry OBJECT-TYPE
       SYNTAX      SmExtsnEntry
       MAX-ACCESS  not-accessible
       STATUS      current
       INDEX { smLangIndex, smExtsnIndex }
       ::= { smExtsnTable 1 }

   SmExtsnEntry ::= SEQUENCE {
       smExtsnIndex        Integer32,
       smExtsnExtension    OBJECT IDENTIFIER,
       smExtsnVersion      SnmpAdminString,
       smExtsnVendor       OBJECT IDENTIFIER,
       smExtsnRevision     SnmpAdminString,





       smExtsnDescr        SnmpAdminString
   }

   smExtsnIndex OBJECT-TYPE
       SYNTAX      Integer32 (1..2147483647)
       MAX-ACCESS  not-accessible
       STATUS      current
       ::= { smExtsnEntry 1}

   smExtsnExtension OBJECT-TYPE
       SYNTAX      OBJECT IDENTIFIER
       MAX-ACCESS  read-only
       STATUS      current
       ::= { smExtsnEntry 2 }

   smExtsnVersion OBJECT-TYPE
       SYNTAX      SnmpAdminString (SIZE (0..32))
       MAX-ACCESS  read-only
       STATUS      current
       ::= { smExtsnEntry 3 }

   smExtsnVendor OBJECT-TYPE
       SYNTAX      OBJECT IDENTIFIER
       MAX-ACCESS  read-only
       STATUS      current
       ::= { smExtsnEntry 4 }





   smExtsnRevision OBJECT-TYPE
       SYNTAX      SnmpAdminString (SIZE (0..32))
       MAX-ACCESS  read-only
       STATUS      current
       ::= { smExtsnEntry 5 }

   smExtsnDescr OBJECT-TYPE
       SYNTAX      SnmpAdminString
       MAX-ACCESS  read-only
       STATUS      current
       ::= { smExtsnEntry 6 }


   smScriptObjects OBJECT IDENTIFIER ::= { smObjects 3 }

   smScriptTable OBJECT-TYPE
       SYNTAX      SEQUENCE OF SmScriptEntry
       MAX-ACCESS  not-accessible
       STATUS      current
       ::= { smScriptObjects 1 }

   smScriptEntry OBJECT-TYPE
       SYNTAX      SmScriptEntry
       MAX-ACCESS  not-accessible
       STATUS      current





       INDEX { smScriptOwner, smScriptName }
       ::= { smScriptTable 1 }

   SmScriptEntry ::= SEQUENCE {
       smScriptOwner       SnmpAdminString,
       smScriptName        SnmpAdminString,
       smScriptDescr       SnmpAdminString,
       smScriptLanguage    Integer32,
       smScriptSource      DisplayString,
       smScriptAdminStatus INTEGER,
       smScriptOperStatus  INTEGER,
       smScriptStorageType StorageType,
       smScriptRowStatus   RowStatus,
       smScriptError       SnmpAdminString,
       smScriptLastChange  DateAndTime
   }

   smScriptOwner OBJECT-TYPE
       SYNTAX      SnmpAdminString (SIZE (0..32))
       MAX-ACCESS  not-accessible
       STATUS      current
       ::= { smScriptEntry 1 }

   smScriptName OBJECT-TYPE
       SYNTAX      SnmpAdminString (SIZE (1..32))
       MAX-ACCESS  not-accessible
       STATUS      current
       ::= { smScriptEntry 2 }

   smScriptDescr OBJECT-TYPE
       SYNTAX      SnmpAdminString
       MAX-ACCESS  read-create
       STATUS      current
       ::= { smScriptEntry 3 }

   smScriptLanguage OBJECT-TYPE
       SYNTAX      Integer32 (0..2147483647)
       MAX-ACCESS  read-create
       STATUS      current
       ::= { smScriptEntry 4 }

   smScriptSource OBJECT-TYPE
       SYNTAX      DisplayString
       MAX-ACCESS  read-create
       STATUS      current
       DEFVAL { ''H }
       ::= { smScriptEntry 5 }

   smScriptAdminStatus OBJECT-TYPE
       SYNTAX      INTEGER {
                       enabled(1),
                       disabled(2),
                       editing(3)
                   }
       MAX-ACCESS  read-create
       STATUS      current
       DEFVAL { disabled }
       ::= { smScriptEntry 6 }

   smScriptOperStatus OBJECT-TYPE
       SYNTAX      INTEGER {
                       enabled(1),
                       disabled(2),
                       editing(3),
                       retrieving(4),
                       compiling(5),
                       noSuchScript(6),
                       accessDenied(7),
                       wrongLanguage(8),
                       wrongVersion(9),
                       compilationFailed(10),
                       noResourcesLeft(11),
                       unknownProtocol(12),
                       protocolFailure(13),
                       genericError(14)
                   }
       MAX-ACCESS  read-only
       STATUS      current
       DEFVAL { disabled }
       ::= { smScriptEntry 7 }

   smScriptStorageType OBJECT-TYPE
       SYNTAX      StorageType
       MAX-ACCESS  read-create
       STATUS      current
       DEFVAL { volatile }
       ::= { smScriptEntry 8 }

   smScriptRowStatus OBJECT-TYPE
       SYNTAX      RowStatus
       MAX-ACCESS  read-create
       STATUS      current
       ::= { smScriptEntry 9 }

   smScriptError OBJECT-TYPE
       SYNTAX      SnmpAdminString
       MAX-ACCESS  read-only
       STATUS      current
       DEFVAL { ''H }
       ::= { smScriptEntry 10 }

   smScriptLastChange OBJECT-TYPE
       SYNTAX      DateAndTime
       MAX-ACCESS  read-only
       STATUS      current
       DEFVAL { '0000000000000000'H }
       ::= { smScriptEntry 11 }


   smCodeTable OBJECT-TYPE
       SYNTAX      SEQUENCE OF SmCodeEntry
       MAX-ACCESS  not-accessible
       STATUS      current
       ::= { smScriptObjects 2 }

   smCodeEntry OBJECT-TYPE
       SYNTAX      SmCodeEntry
       MAX-ACCESS  not-accessible
       STATUS      current
       INDEX { smScriptOwner, smScriptName, smCodeIndex }
       ::= { smCodeTable 1 }

   SmCodeEntry ::= SEQUENCE {
       smCodeIndex         Unsigned32,





       smCodeText          OCTET STRING,
       smCodeRowStatus     RowStatus
   }

   smCodeIndex OBJECT-TYPE
       SYNTAX      Unsigned32 (1..4294967295)
       MAX-ACCESS  not-accessible
       STATUS      current
       ::= { smCodeEntry 1 }

   smCodeText OBJECT-TYPE
       SYNTAX      OCTET STRING (SIZE (1..1024))
       MAX-ACCESS  read-create
       STATUS      current
       ::= { smCodeEntry 2 }

   smCodeRowStatus OBJECT-TYPE
       SYNTAX      RowStatus
       MAX-ACCESS  read-create
       STATUS      current
       ::= { smCodeEntry 3 }


   smRunObjects OBJECT IDENTIFIER ::= { smObjects 4 }

   smLaunchTable OBJECT-TYPE
       SYNTAX      SEQUENCE OF SmLaunchEntry
       MAX-ACCESS  not-accessible





       STATUS      current
       ::= { smRunObjects 1 }

   smLaunchEntry OBJECT-TYPE
       SYNTAX      SmLaunchEntry
       MAX-ACCESS  not-accessible
       STATUS      current
       INDEX { smLaunchOwner, smLaunchName }
       ::= { smLaunchTable 1 }

   SmLaunchEntry ::= SEQUENCE {
       smLaunchOwner               SnmpAdminString,
       smLaunchName                SnmpAdminString,
       smLaunchScriptOwner         SnmpAdminString,
       smLaunchScriptName          SnmpAdminString,
       smLaunchArgument            OCTET STRING,
       smLaunchMaxRunning          Unsigned32,
       smLaunchMaxCompleted        Unsigned32,
       smLaunchLifeTime            TimeInterval,
       smLaunchExpireTime          TimeInterval,
       smLaunchStart               Integer32,
       smLaunchControl             INTEGER,
       smLaunchAdminStatus         INTEGER,
       smLaunchOperStatus          INTEGER,
       smLaunchRunIndexNext        Integer32,
       smLaunchStorageType         StorageType,
       smLaunchRowStatus           RowStatus,
       smLaunchError               SnmpAdminString,
       smLaunchLastChange          DateAndTime,
       smLaunchRowExpireTime       TimeInterval
   }

   smLaunchOwner OBJECT-TYPE
       SYNTAX      SnmpAdminString (SIZE (0..32))
       MAX-ACCESS  not-accessible
       STATUS      current





       ::= { smLaunchEntry 1 }

   smLaunchName OBJECT-TYPE
       SYNTAX      SnmpAdminString (SIZE (1..32))
       MAX-ACCESS  not-accessible
       STATUS      current
       ::= { smLaunchEntry 2 }

   smLaunchScriptOwner OBJECT-TYPE
       SYNTAX      SnmpAdminString (SIZE (0..32))
       MAX-ACCESS  read-create
       STATUS      current
       ::= { smLaunchEntry 3 }

   smLaunchScriptName OBJECT-TYPE
       SYNTAX      SnmpAdminString (SIZE (0..32))
       MAX-ACCESS  read-create
       STATUS      current
       DEFVAL { ''H }
       ::= { smLaunchEntry 4 }

   smLaunchArgument OBJECT-TYPE
       SYNTAX      OCTET STRING





       MAX-ACCESS  read-create
       STATUS      current
       DEFVAL { ''H }
       ::= { smLaunchEntry 5 }

   smLaunchMaxRunning OBJECT-TYPE
       SYNTAX      Unsigned32 (1..4294967295)
       MAX-ACCESS  read-create
       STATUS      current
       DEFVAL { 1 }
       ::= { smLaunchEntry 6 }

   smLaunchMaxCompleted OBJECT-TYPE
       SYNTAX      Unsigned32 (1..4294967295)
       MAX-ACCESS  read-create
       STATUS      current
       DEFVAL { 1 }
       ::= { smLaunchEntry 7 }

   smLaunchLifeTime OBJECT-TYPE
       SYNTAX      TimeInterval
       UNITS       "centi-seconds"
       MAX-ACCESS  read-create
       STATUS      current
       DEFVAL { 360000 }
       ::= { smLaunchEntry 8 }

   smLaunchExpireTime OBJECT-TYPE
       SYNTAX      TimeInterval
       UNITS       "centi-seconds"
       MAX-ACCESS  read-create
       STATUS      current
       DEFVAL { 360000 }
       ::= { smLaunchEntry 9 }

   smLaunchStart OBJECT-TYPE
       SYNTAX      Integer32 (0..2147483647)
       MAX-ACCESS  read-create
       STATUS      current
       DEFVAL { 0 }
       ::= { smLaunchEntry 10 }

   smLaunchControl OBJECT-TYPE
       SYNTAX      INTEGER {
                       abort(1),
                       suspend(2),
                       resume(3),
                       nop(4)
                   }
       MAX-ACCESS  read-create
       STATUS      current
       DEFVAL { nop }
       ::= { smLaunchEntry 11 }

   smLaunchAdminStatus OBJECT-TYPE
       SYNTAX      INTEGER {
                       enabled(1),
                       disabled(2),
                       autostart(3)
                   }
       MAX-ACCESS  read-create
       STATUS      current
       DEFVAL { disabled }
       ::= { smLaunchEntry 12 }

   smLaunchOperStatus OBJECT-TYPE
       SYNTAX      INTEGER {
                       enabled(1),
                       disabled(2),
                       expired(3)
                   }
       MAX-ACCESS  read-only
       STATUS      current
       DEFVAL { disabled }
       ::= { smLaunchEntry 13 }

   smLaunchRunIndexNext OBJECT-TYPE
       SYNTAX      Integer32 (1..2147483647)
       MAX-ACCESS  read-only
       STATUS      current
       ::= { smLaunchEntry 14 }

   smLaunchStorageType OBJECT-TYPE
       SYNTAX      StorageType
       MAX-ACCESS  read-create
       STATUS      current
       DEFVAL { volatile }
       ::= { smLaunchEntry 15 }

   smLaunchRowStatus OBJECT-TYPE
       SYNTAX      RowStatus
       MAX-ACCESS  read-create
       STATUS      current
       ::= { smLaunchEntry 16 }

   smLaunchError OBJECT-TYPE
       SYNTAX      SnmpAdminString
       MAX-ACCESS  read-only
       STATUS      current
       DEFVAL { ''H }
       ::= { smLaunchEntry 17 }

   smLaunchLastChange OBJECT-TYPE
       SYNTAX      DateAndTime
       MAX-ACCESS  read-only
       STATUS      current
       DEFVAL { '0000000000000000'H }
       ::= { smLaunchEntry 18 }

   smLaunchRowExpireTime OBJECT-TYPE
       SYNTAX      TimeInterval
       UNITS       "centi-seconds"
       MAX-ACCESS  read-create
       STATUS      current
       DEFVAL { 2147483647 }
       ::= { smLaunchEntry 19 }


   smRunTable OBJECT-TYPE
       SYNTAX      SEQUENCE OF SmRunEntry
       MAX-ACCESS  not-accessible
       STATUS      current
       ::= { smRunObjects 2 }

   smRunEntry OBJECT-TYPE
       SYNTAX      SmRunEntry
       MAX-ACCESS  not-accessible
       STATUS      current
       INDEX { smLaunchOwner, smLaunchName, smRunIndex }
       ::= { smRunTable 1 }

   SmRunEntry ::= SEQUENCE {
       smRunIndex          Integer32,





       smRunArgument       OCTET STRING,
       smRunStartTime      DateAndTime,
       smRunEndTime        DateAndTime,
       smRunLifeTime       TimeInterval,
       smRunExpireTime     TimeInterval,
       smRunExitCode       INTEGER,
       smRunResult         OCTET STRING,
       smRunControl        INTEGER,
       smRunState          INTEGER,
       smRunError          SnmpAdminString,
       smRunResultTime     DateAndTime,
       smRunErrorTime      DateAndTime
   }

   smRunIndex OBJECT-TYPE
       SYNTAX      Integer32 (1..2147483647)
       MAX-ACCESS  not-accessible
       STATUS      current
       ::= { smRunEntry 1 }

   smRunArgument OBJECT-TYPE
       SYNTAX      OCTET STRING
       MAX-ACCESS  read-only
       STATUS      current
       DEFVAL { ''H }
       ::= { smRunEntry 2 }

   smRunStartTime OBJECT-TYPE
       SYNTAX      DateAndTime
       MAX-ACCESS  read-only
       STATUS      current
       DEFVAL { '0000000000000000'H }
       ::= { smRunEntry 3 }





   smRunEndTime OBJECT-TYPE
       SYNTAX      DateAndTime
       MAX-ACCESS  read-only
       STATUS      current
       DEFVAL { '0000000000000000'H }
       ::= { smRunEntry 4 }

   smRunLifeTime OBJECT-TYPE
       SYNTAX      TimeInterval
       UNITS       "centi-seconds"
       MAX-ACCESS  read-write
       STATUS      current
       ::= { smRunEntry 5 }






   smRunExpireTime OBJECT-TYPE
       SYNTAX      TimeInterval
       UNITS       "centi-seconds"
       MAX-ACCESS  read-write
       STATUS      current
       ::= { smRunEntry 6 }

   smRunExitCode OBJECT-TYPE
       SYNTAX      INTEGER {
                       noError(1),
                       halted(2),
                       lifeTimeExceeded(3),
                       noResourcesLeft(4),
                       languageError(5),
                       runtimeError(6),
                       invalidArgument(7),
                       securityViolation(8),
                       genericError(9)
                   }
       MAX-ACCESS  read-only
       STATUS      current
       DEFVAL { noError }
       ::= { smRunEntry 7 }

   smRunResult OBJECT-TYPE
       SYNTAX      OCTET STRING
       MAX-ACCESS  read-only
       STATUS      current
       DEFVAL { ''H }
       ::= { smRunEntry 8 }

   smRunControl OBJECT-TYPE
       SYNTAX      INTEGER {
                       abort(1),
                       suspend(2),
                       resume(3),
                       nop(4)
                   }
       MAX-ACCESS  read-write
       STATUS      current
       DEFVAL { nop }
       ::= { smRunEntry 9 }

   smRunState OBJECT-TYPE
       SYNTAX      INTEGER {
                       initializing(1),
                       executing(2),
                       suspending(3),
                       suspended(4),
                       resuming(5),
                       aborting(6),
                       terminated(7)
                   }
       MAX-ACCESS  read-only
       STATUS      current
       ::= { smRunEntry 10 }

   smRunError OBJECT-TYPE
       SYNTAX      SnmpAdminString
       MAX-ACCESS  read-only
       STATUS      current
       DEFVAL { ''H }
       ::= { smRunEntry 11 }

   smRunResultTime OBJECT-TYPE
       SYNTAX      DateAndTime
       MAX-ACCESS  read-only
       STATUS      current
       DEFVAL { '0000000000000000'H }
       ::= { smRunEntry 12 }

   smRunErrorTime OBJECT-TYPE
       SYNTAX      DateAndTime
       MAX-ACCESS  read-only
       STATUS      current
       DEFVAL { '0000000000000000'H }
       ::= { smRunEntry 13 }


   smTraps OBJECT IDENTIFIER ::= { smNotifications 0 }

   smScriptAbort NOTIFICATION-TYPE
       OBJECTS     { smRunExitCode, smRunEndTime, smRunError }
       STATUS      current
       ::= { smTraps 1 }

   smScriptResult NOTIFICATION-TYPE
       OBJECTS     { smRunResult }
       STATUS      current
       ::= { smTraps 2 }

   smScriptException NOTIFICATION-TYPE
       OBJECTS     { smRunError }
       STATUS      current
       ::= { smTraps 3 }






   smCompliances OBJECT IDENTIFIER ::= { smConformance 1 }
   smGroups      OBJECT IDENTIFIER ::= { smConformance 2 }


   smCompliance2 MODULE-COMPLIANCE
       STATUS      current
       MODULE      -- this module
       MANDATORY-GROUPS {
               smLanguageGroup, smScriptGroup2, smLaunchGroup2,
               smRunGroup2, smNotificationsGroup2
       }
       GROUP   smCodeGroup
       OBJECT  smScriptSource
       MIN-ACCESS  read-only
       OBJECT smCodeText
       OBJECT smLaunchArgument
       OBJECT smRunArgument
       OBJECT smRunResult
       OBJECT smRunState





       ::= { smCompliances 2 }

   smLanguageGroup OBJECT-GROUP
       OBJECTS {
           smLangLanguage, smLangVersion,
           smLangVendor, smLangRevision,
           smLangDescr, smExtsnExtension,
           smExtsnVersion, smExtsnVendor,
           smExtsnRevision, smExtsnDescr
       }
       STATUS      current
       ::= { smGroups 1 }

   smScriptGroup2 OBJECT-GROUP
       OBJECTS {
           smScriptDescr, smScriptLanguage,
           smScriptSource, smScriptAdminStatus,
           smScriptOperStatus, smScriptStorageType,
           smScriptRowStatus, smScriptError,
           smScriptLastChange
       }
       STATUS      current
       ::= { smGroups 7 }

   smCodeGroup OBJECT-GROUP
       OBJECTS {
           smCodeText, smCodeRowStatus
       }
       STATUS      current
       ::= { smGroups 3 }

   smLaunchGroup2 OBJECT-GROUP
       OBJECTS {
           smLaunchScriptOwner, smLaunchScriptName,
           smLaunchArgument, smLaunchMaxRunning,
           smLaunchMaxCompleted, smLaunchLifeTime,
           smLaunchExpireTime, smLaunchStart,
           smLaunchControl, smLaunchAdminStatus,
           smLaunchOperStatus, smLaunchRunIndexNext,





           smLaunchStorageType, smLaunchRowStatus,
           smLaunchError, smLaunchLastChange,
           smLaunchRowExpireTime
       }
       STATUS      current
       ::= { smGroups 8 }

   smRunGroup2 OBJECT-GROUP
       OBJECTS {
           smRunArgument, smRunStartTime,
           smRunEndTime, smRunLifeTime,
           smRunExpireTime, smRunExitCode,
           smRunResult, smRunState,
           smRunControl, smRunError,
           smRunResultTime, smRunErrorTime
       }
       STATUS      current
       ::= { smGroups 9 }

   smNotificationsGroup2 NOTIFICATION-GROUP
       NOTIFICATIONS {
           smScriptAbort,
           smScriptResult,
           smScriptException
       }
       STATUS      current
       ::= { smGroups 10 }


   smCompliance MODULE-COMPLIANCE
       STATUS      deprecated
       MODULE      -- this module
       MANDATORY-GROUPS {





               smLanguageGroup, smScriptGroup, smLaunchGroup, smRunGroup
       }
       GROUP   smCodeGroup
       OBJECT  smScriptSource
       MIN-ACCESS  read-only
       OBJECT smCodeText
       OBJECT smLaunchArgument
       OBJECT smRunArgument
       OBJECT smRunResult
       OBJECT smRunState
       ::= { smCompliances 1 }

   smScriptGroup OBJECT-GROUP
       OBJECTS {
           smScriptDescr, smScriptLanguage,
           smScriptSource, smScriptAdminStatus,
           smScriptOperStatus, smScriptStorageType,
           smScriptRowStatus
       }
       STATUS      deprecated





       ::= { smGroups 2 }

   smLaunchGroup OBJECT-GROUP
       OBJECTS {
           smLaunchScriptOwner, smLaunchScriptName,
           smLaunchArgument, smLaunchMaxRunning,
           smLaunchMaxCompleted, smLaunchLifeTime,
           smLaunchExpireTime, smLaunchStart,
           smLaunchControl, smLaunchAdminStatus,
           smLaunchOperStatus, smLaunchRunIndexNext,
           smLaunchStorageType, smLaunchRowStatus
       }
       STATUS      deprecated
       ::= { smGroups 4 }

   smRunGroup OBJECT-GROUP
       OBJECTS {
           smRunArgument, smRunStartTime,
           smRunEndTime, smRunLifeTime,
           smRunExpireTime, smRunExitCode,
           smRunResult, smRunState,
           smRunControl, smRunError
       }
       STATUS      deprecated
       ::= { smGroups 5 }

   smNotificationsGroup NOTIFICATION-GROUP
       NOTIFICATIONS {
           smScriptAbort,
           smScriptResult
       }
       STATUS      deprecated
       ::= { smGroups 6 }

   END

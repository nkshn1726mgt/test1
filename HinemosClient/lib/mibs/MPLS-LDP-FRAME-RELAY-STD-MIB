MPLS-LDP-FRAME-RELAY-STD-MIB DEFINITIONS ::= BEGIN

   IMPORTS
       OBJECT-TYPE,
       MODULE-IDENTITY,
       Unsigned32
           FROM SNMPv2-SMI                                 --  [RFC2578]
       MODULE-COMPLIANCE,
       OBJECT-GROUP
           FROM SNMPv2-CONF                                --  [RFC2580]

       RowStatus,
       StorageType





           FROM SNMPv2-TC                                  --  [RFC2579]

       DLCI
           FROM FRAME-RELAY-DTE-MIB                        --  [RFC2115]

       InterfaceIndexOrZero
           FROM IF-MIB                                     --  [RFC2020]

       mplsStdMIB
           FROM MPLS-TC-STD-MIB                            --  [RFC3811]

       mplsLdpEntityLdpId,
       mplsLdpEntityIndex,
       mplsLdpPeerLdpId
           FROM MPLS-LDP-STD-MIB                           --  [RFC3813]
       ;

   mplsLdpFrameRelayStdMIB MODULE-IDENTITY
       LAST-UPDATED "200406030000Z"  -- June 3, 2004
       ORGANIZATION "Multiprotocol Label Switching (mpls)
                     Working Group"






       ::= { mplsStdMIB 6 }


   mplsLdpFrameRelayObjects  OBJECT IDENTIFIER
                              ::= { mplsLdpFrameRelayStdMIB 1 }

   mplsLdpFrameRelayConformance   OBJECT IDENTIFIER
                              ::= { mplsLdpFrameRelayStdMIB 2 }



   mplsLdpEntityFrameRelayObjects OBJECT IDENTIFIER ::=
                                       { mplsLdpFrameRelayObjects 1 }

   mplsLdpEntityFrameRelayTable  OBJECT-TYPE
       SYNTAX      SEQUENCE OF MplsLdpEntityFrameRelayEntry
       MAX-ACCESS  not-accessible
       STATUS      current
       ::= { mplsLdpEntityFrameRelayObjects 1 }

   mplsLdpEntityFrameRelayEntry OBJECT-TYPE
       SYNTAX      MplsLdpEntityFrameRelayEntry
       MAX-ACCESS  not-accessible
       STATUS      current
       INDEX       {  mplsLdpEntityLdpId,
                      mplsLdpEntityIndex





                   }
       ::= { mplsLdpEntityFrameRelayTable 1 }

   MplsLdpEntityFrameRelayEntry ::= SEQUENCE {
       mplsLdpEntityFrameRelayIfIndexOrZero        InterfaceIndexOrZero,
       mplsLdpEntityFrameRelayMergeCap             INTEGER,
       mplsLdpEntityFrameRelayLRComponents         Unsigned32,
       mplsLdpEntityFrameRelayVcDirectionality     INTEGER,
       mplsLdpEntityFrameRelayStorageType          StorageType,
       mplsLdpEntityFrameRelayRowStatus            RowStatus
   }

   mplsLdpEntityFrameRelayIfIndexOrZero OBJECT-TYPE
       SYNTAX      InterfaceIndexOrZero
       MAX-ACCESS  read-create
       STATUS      current
       ::= { mplsLdpEntityFrameRelayEntry 1 }

   mplsLdpEntityFrameRelayMergeCap OBJECT-TYPE
       SYNTAX      INTEGER {
                       notSupported(0),
                       supported(1)
                   }
       MAX-ACCESS  read-create
       STATUS      current
       ::= { mplsLdpEntityFrameRelayEntry 2 }

   mplsLdpEntityFrameRelayLRComponents OBJECT-TYPE
       SYNTAX      Unsigned32 (1..65535)
       MAX-ACCESS  read-only
       STATUS      current
       ::= { mplsLdpEntityFrameRelayEntry 3 }

   mplsLdpEntityFrameRelayVcDirectionality OBJECT-TYPE
       SYNTAX      INTEGER {
                             bidirectional(0),
                             unidirection(1)
                           }
       MAX-ACCESS  read-create
       STATUS      current
       ::= { mplsLdpEntityFrameRelayEntry 4 }





   mplsLdpEntityFrameRelayStorageType  OBJECT-TYPE
       SYNTAX      StorageType
       MAX-ACCESS  read-create
       STATUS      current
       DEFVAL { nonVolatile }
       ::= { mplsLdpEntityFrameRelayEntry 5 }

   mplsLdpEntityFrameRelayRowStatus OBJECT-TYPE
       SYNTAX      RowStatus
       MAX-ACCESS  read-create
       STATUS      current
       ::= { mplsLdpEntityFrameRelayEntry 6 }


   mplsLdpEntityFrameRelayLRTable  OBJECT-TYPE
       SYNTAX      SEQUENCE OF MplsLdpEntityFrameRelayLREntry
       MAX-ACCESS  not-accessible
       STATUS      current
       ::= { mplsLdpEntityFrameRelayObjects 2 }

   mplsLdpEntityFrameRelayLREntry OBJECT-TYPE
       SYNTAX      MplsLdpEntityFrameRelayLREntry
       MAX-ACCESS  not-accessible
       STATUS      current
       INDEX       {  mplsLdpEntityLdpId,
                      mplsLdpEntityIndex,
                      mplsLdpEntityFrameRelayLRMinDlci
                   }
       ::= { mplsLdpEntityFrameRelayLRTable 1 }

   MplsLdpEntityFrameRelayLREntry ::= SEQUENCE {
       mplsLdpEntityFrameRelayLRMinDlci              DLCI,
       mplsLdpEntityFrameRelayLRMaxDlci              DLCI,
       mplsLdpEntityFrameRelayLRLen                  INTEGER,
       mplsLdpEntityFrameRelayLRStorageType          StorageType,
       mplsLdpEntityFrameRelayLRRowStatus            RowStatus
   }

   mplsLdpEntityFrameRelayLRMinDlci OBJECT-TYPE
       SYNTAX      DLCI
       MAX-ACCESS  not-accessible
       STATUS      current
       ::= { mplsLdpEntityFrameRelayLREntry 1 }






   mplsLdpEntityFrameRelayLRMaxDlci OBJECT-TYPE
       SYNTAX      DLCI
       MAX-ACCESS  read-create
       STATUS      current
       ::= { mplsLdpEntityFrameRelayLREntry 2 }

   mplsLdpEntityFrameRelayLRLen OBJECT-TYPE
       SYNTAX      INTEGER {
                       tenDlciBits(0),
                       twentyThreeDlciBits(2)
                   }
       MAX-ACCESS  read-create
       STATUS      current
       ::= { mplsLdpEntityFrameRelayLREntry 3 }

   mplsLdpEntityFrameRelayLRStorageType  OBJECT-TYPE
       SYNTAX      StorageType
       MAX-ACCESS  read-create
       STATUS      current
       DEFVAL { nonVolatile }
       ::= { mplsLdpEntityFrameRelayLREntry 4 }

   mplsLdpEntityFrameRelayLRRowStatus OBJECT-TYPE
       SYNTAX      RowStatus
       MAX-ACCESS  read-create
       STATUS      current
       ::= { mplsLdpEntityFrameRelayLREntry 5 }


   mplsLdpFrameRelaySessionObjects  OBJECT IDENTIFIER ::=
                              { mplsLdpFrameRelayObjects  2 }

   mplsLdpFrameRelaySessionTable OBJECT-TYPE
       SYNTAX      SEQUENCE OF MplsLdpFrameRelaySessionEntry
       MAX-ACCESS  not-accessible
       STATUS      current
       ::= { mplsLdpFrameRelaySessionObjects 1 }

   mplsLdpFrameRelaySessionEntry OBJECT-TYPE
       SYNTAX      MplsLdpFrameRelaySessionEntry
       MAX-ACCESS  not-accessible
       STATUS      current
       INDEX       { mplsLdpEntityLdpId,
                     mplsLdpEntityIndex,
                     mplsLdpPeerLdpId,
                     mplsLdpFrameRelaySessionMinDlci
                   }
       ::= { mplsLdpFrameRelaySessionTable 1 }

   MplsLdpFrameRelaySessionEntry ::= SEQUENCE {
       mplsLdpFrameRelaySessionMinDlci    DLCI,
       mplsLdpFrameRelaySessionMaxDlci    DLCI,
       mplsLdpFrameRelaySessionLen        INTEGER
   }

   mplsLdpFrameRelaySessionMinDlci OBJECT-TYPE
       SYNTAX      DLCI
       MAX-ACCESS  not-accessible
       STATUS      current
       ::= { mplsLdpFrameRelaySessionEntry 1 }

   mplsLdpFrameRelaySessionMaxDlci OBJECT-TYPE
       SYNTAX      DLCI
       MAX-ACCESS  read-only
       STATUS      current
       ::= { mplsLdpFrameRelaySessionEntry 2 }





   mplsLdpFrameRelaySessionLen OBJECT-TYPE
       SYNTAX      INTEGER {
                       tenDlciBits(0),
                       twentyThreeDlciBits(2)
                   }
       MAX-ACCESS  read-only
       STATUS      current
       ::= { mplsLdpFrameRelaySessionEntry 3 }


   mplsLdpFrameRelayGroups
       OBJECT IDENTIFIER ::= { mplsLdpFrameRelayConformance 1 }

   mplsLdpFrameRelayCompliances
       OBJECT IDENTIFIER ::= { mplsLdpFrameRelayConformance 2 }


   mplsLdpFrameRelayModuleFullCompliance MODULE-COMPLIANCE
       STATUS current
       MODULE -- this module
           MANDATORY-GROUPS    {
                                  mplsLdpFrameRelayGroup
                               }

       OBJECT       mplsLdpEntityFrameRelayRowStatus
       SYNTAX       RowStatus { active(1) }
       WRITE-SYNTAX RowStatus { createAndGo(4), destroy(6) }

       OBJECT       mplsLdpEntityFrameRelayLRRowStatus
       SYNTAX       RowStatus { active(1) }
       WRITE-SYNTAX RowStatus { createAndGo(4), destroy(6) }





       ::= { mplsLdpFrameRelayCompliances 1 }


   mplsLdpFrameRelayModuleReadOnlyCompliance MODULE-COMPLIANCE
       STATUS current
       MODULE -- this module
           MANDATORY-GROUPS    {
                                  mplsLdpFrameRelayGroup
                               }

       OBJECT       mplsLdpEntityFrameRelayIfIndexOrZero
       MIN-ACCESS   read-only

       OBJECT       mplsLdpEntityFrameRelayMergeCap
       MIN-ACCESS   read-only

       OBJECT       mplsLdpEntityFrameRelayVcDirectionality
       MIN-ACCESS   read-only

       OBJECT       mplsLdpEntityFrameRelayStorageType
       MIN-ACCESS   read-only

       OBJECT       mplsLdpEntityFrameRelayRowStatus
       SYNTAX       RowStatus { active(1) }
       MIN-ACCESS   read-only

       OBJECT       mplsLdpEntityFrameRelayLRMaxDlci
       MIN-ACCESS   read-only





       OBJECT       mplsLdpEntityFrameRelayLRLen
       MIN-ACCESS   read-only

       OBJECT       mplsLdpEntityFrameRelayLRStorageType
       MIN-ACCESS   read-only

       OBJECT       mplsLdpEntityFrameRelayLRRowStatus
       SYNTAX       RowStatus { active(1) }
       MIN-ACCESS   read-only
       ::= { mplsLdpFrameRelayCompliances 2 }


   mplsLdpFrameRelayGroup OBJECT-GROUP
       OBJECTS {
       mplsLdpEntityFrameRelayIfIndexOrZero,
       mplsLdpEntityFrameRelayMergeCap,
       mplsLdpEntityFrameRelayLRComponents,
       mplsLdpEntityFrameRelayVcDirectionality,
       mplsLdpEntityFrameRelayStorageType,
       mplsLdpEntityFrameRelayRowStatus,
       mplsLdpEntityFrameRelayLRMaxDlci,
       mplsLdpEntityFrameRelayLRLen,
       mplsLdpEntityFrameRelayLRStorageType,
       mplsLdpEntityFrameRelayLRRowStatus,
       mplsLdpFrameRelaySessionMaxDlci,
       mplsLdpFrameRelaySessionLen
       }
       STATUS    current
       ::= { mplsLdpFrameRelayGroups 1 }

   END

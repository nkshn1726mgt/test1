ISNS-MIB DEFINITIONS ::= BEGIN
      IMPORTS
          MODULE-IDENTITY,
          OBJECT-TYPE,
          NOTIFICATION-TYPE,
          Integer32,
          Unsigned32,
          Gauge32,
          mib-2
               FROM SNMPv2-SMI

          TEXTUAL-CONVENTION,
          TimeStamp,
          TruthValue
               FROM SNMPv2-TC

          OBJECT-GROUP,
          MODULE-COMPLIANCE,
          NOTIFICATION-GROUP
               FROM SNMPv2-CONF

          SnmpAdminString
               FROM SNMP-FRAMEWORK-MIB

          InetAddressType,
          InetAddress,
          InetPortNumber
               FROM INET-ADDRESS-MIB

          FcNameIdOrZero,
          FcAddressIdOrZero
               FROM FC-MGMT-MIB

          PhysicalIndex
               FROM ENTITY-MIB
            ;

      isnsMIB  MODULE-IDENTITY
            LAST-UPDATED "200707110000Z"





            ORGANIZATION "IETF IPS Working Group"



                 ::=  { mib-2 163 }








      IsnsDiscoveryDomainSetId ::= TEXTUAL-CONVENTION
          DISPLAY-HINT   "d"
          STATUS         current
          SYNTAX         Unsigned32 ( 1 .. 4294967295 )

      IsnsDdsStatusType ::= TEXTUAL-CONVENTION
          STATUS         current
          SYNTAX         BITS {
              reserved0(0), reserved1(1), reserved2(2),
              reserved3(3), reserved4(4), reserved5(5),
              reserved6(6), reserved7(7), reserved8(8),
              reserved9(9), reserved10(10), reserved11(11),
              reserved12(12), reserved13(13), reserved14(14),
              reserved15(15), reserved16(16), reserved17(17),
              reserved18(18), reserved19(19), reserved20(20),
              reserved21(21), reserved22(22), reserved23(23),
              reserved24(24), reserved25(25), reserved26(26),
              reserved27(27), reserved28(28), reserved29(29),
              reserved30(30),
              ddsEnabled (31)
                              }

      IsnsDiscoveryDomainId ::= TEXTUAL-CONVENTION
          DISPLAY-HINT   "d"
          STATUS         current
          SYNTAX         Unsigned32 ( 1 .. 4294967295 )

      IsnsDdFeatureType ::= TEXTUAL-CONVENTION
          STATUS         current
          SYNTAX         BITS {
              reserved0(0), reserved1(1), reserved2(2),
              reserved3(3), reserved4(4), reserved5(5),
              reserved6(6), reserved7(7), reserved8(8),
              reserved9(9), reserved10(10), reserved11(11),
              reserved12(12), reserved13(13), reserved14(14),
              reserved15(15), reserved16(16), reserved17(17),
              reserved18(18), reserved19(19), reserved20(20),
              reserved21(21), reserved22(22), reserved23(23),
              reserved24(24), reserved25(25), reserved26(26),
              reserved27(27), reserved28(28), reserved29(29),
              reserved30(30),
              bootlist(31)
                              }

      IsnsDdDdsModificationType ::= TEXTUAL-CONVENTION
          STATUS         current
          SYNTAX         BITS {
                            controlNode(0),
                            targetIscsiNode(1),
                            initiatorIscsiNode(2),
                            targetIfcpNode(3),
                            initiatorIfcpNode(4)
                              }

      IsnsEntityIndexIdOrZero ::= TEXTUAL-CONVENTION
          DISPLAY-HINT   "d"
          STATUS         current
          SYNTAX         Unsigned32 ( 0 .. 4294967295 )

      IsnsPortalGroupIndexId ::= TEXTUAL-CONVENTION
          DISPLAY-HINT   "d"
          STATUS         current
          SYNTAX         Unsigned32 ( 1 .. 4294967295 )

      IsnsPortalIndexId ::= TEXTUAL-CONVENTION
          DISPLAY-HINT   "d"
          STATUS         current
          SYNTAX         Unsigned32 ( 1 .. 4294967295 )

      IsnsPortalPortTypeId ::= TEXTUAL-CONVENTION
          STATUS         current
          SYNTAX         INTEGER { udp(1), tcp(2) }

      IsnsPortalGroupTagIdOrNull ::= TEXTUAL-CONVENTION
          DISPLAY-HINT   "d"
          STATUS         current
          SYNTAX         Integer32 ( -1 .. 65535 )

      IsnsPortalSecurityType ::= TEXTUAL-CONVENTION
          STATUS         current
          SYNTAX        BITS {
              reserved0(0), reserved1(1), reserved2(2),
              reserved3(3), reserved4(4), reserved5(5),
              reserved6(6), reserved7(7), reserved8(8),
              reserved9(9), reserved10(10), reserved11(11),
              reserved12(12), reserved13(13), reserved14(14),
              reserved15(15), reserved16(16), reserved17(17),
              reserved18(18), reserved19(19), reserved20(20),
              reserved21(21), reserved22(22), reserved23(23),
              reserved24(24),
              tunnelModePreferred(25),
              transportModePreferred(26),
              pfsEnabled(27),
              agressiveModeEnabled(28),
              mainModeEnabled(29),
              ikeIPsecEnabled(30),
              bitmapVALID(31)
                             }

      IsnsNodeIndexId ::= TEXTUAL-CONVENTION
          DISPLAY-HINT   "d"
          STATUS         current
          SYNTAX         Unsigned32 ( 1 .. 4294967295 )

      IsnsIscsiNodeType ::= TEXTUAL-CONVENTION
          STATUS         current
          SYNTAX         BITS {
              reserved0(0), reserved1(1), reserved2(2),
              reserved3(3), reserved4(4), reserved5(5),
              reserved6(6), reserved7(7), reserved8(8),
              reserved9(9), reserved10(10), reserved11(11),
              reserved12(12), reserved13(13), reserved14(14),
              reserved15(15), reserved16(16), reserved17(17),
              reserved18(18), reserved19(19), reserved20(20),
              reserved21(21), reserved22(22), reserved23(23),
              reserved24(24), reserved25(25), reserved26(26),
              reserved27(27), reserved28(28),
              control(29),
              initiator(30),
              target(31)
                              }

      IsnsFcClassOfServiceType ::= TEXTUAL-CONVENTION
          STATUS         current
          SYNTAX         BITS {
              reserved0(0), reserved1(1), reserved2(2),
              reserved3(3), reserved4(4), reserved5(5),
              reserved6(6), reserved7(7), reserved8(8),





              reserved9(9), reserved10(10), reserved11(11),
              reserved12(12), reserved13(13), reserved14(14),
              reserved15(15), reserved16(16), reserved17(17),
              reserved18(18), reserved19(19), reserved20(20),
              reserved21(21), reserved22(22), reserved23(23),
              reserved24(24), reserved25(25), reserved26(26),
              reserved27(27),
              class3(28),
              class2(29)
                              }

      IsnsIscsiScnType ::= TEXTUAL-CONVENTION
          STATUS         current
          SYNTAX         BITS {
              reserved0(0), reserved1(1), reserved2(2),
              reserved3(3), reserved4(4), reserved5(5),
              reserved6(6), reserved7(7), reserved8(8),
              reserved9(9), reserved10(10), reserved11(11),
              reserved12(12), reserved13(13), reserved14(14),
              reserved15(15), reserved16(16), reserved17(17),
              reserved18(18), reserved19(19), reserved20(20),
              reserved21(21), reserved22(22), reserved23(23),
              initiatorAndSelfOnly(24),
              targetAndSelfOnly(25),
              managementRegistrationScn(26),
              objectRemoved(27),
              objectAdded(28),





              objectUpdated(29),
              ddOrDdsMemberRemoved(30),
              ddOrDdsMemberAdded(31)
                              }

      IsnsIfcpScnType ::= TEXTUAL-CONVENTION
          STATUS         current
          SYNTAX         BITS {
              reserved0(0), reserved1(1), reserved2(2),
              reserved3(3), reserved4(4), reserved5(5),
              reserved6(6), reserved7(7), reserved8(8),
              reserved9(9), reserved10(10), reserved11(11),
              reserved12(12), reserved13(13), reserved14(14),
              reserved15(15), reserved16(16), reserved17(17),
              reserved18(18), reserved19(19), reserved20(20),
              reserved21(21), reserved22(22), reserved23(23),
              initiatorAndSelfOnly(24),
              targetAndSelfOnly(25),
              managementRegistrationScn(26),
              objectRemoved(27),
              objectAdded(28),
              objectUpdated(29),
              ddOrDdsMemberRemoved(30),
              ddOrDdsMemberAdded(31)
                              }

      IsnsFcPortRoleType ::= TEXTUAL-CONVENTION





          STATUS         current
          SYNTAX         BITS {
              reserved0(0), reserved1(1), reserved2(2),
              reserved3(3), reserved4(4), reserved5(5),
              reserved6(6), reserved7(7), reserved8(8),
              reserved9(9), reserved10(10), reserved11(11),
              reserved12(12), reserved13(13), reserved14(14),
              reserved15(15), reserved16(16), reserved17(17),
              reserved18(18), reserved19(19), reserved20(20),
              reserved21(21), reserved22(22), reserved23(23),
              reserved24(24), reserved25(25), reserved26(26),
              reserved27(27), reserved28(28),
              control(29),
              initiator(30),
              target(31)
                              }

      IsnsSrvrDiscoveryMethodsType ::= TEXTUAL-CONVENTION
          STATUS         current
          SYNTAX         BITS {
                            dhcp(0),
                            slp(1),
                            multicastGroupHb(2),
                            broadcastHb(3),





                            cfgdServerList(4),
                            other(5)
                                  }



      isnsNotifications           OBJECT IDENTIFIER ::=
                                      { isnsMIB 0 }
      isnsObjects                 OBJECT IDENTIFIER ::=
                                      { isnsMIB 1 }
      isnsConformance             OBJECT IDENTIFIER ::=
                                      { isnsMIB 2 }


      isnsServerInfo OBJECT IDENTIFIER ::= { isnsObjects 1 }

      isnsServerTable             OBJECT-TYPE
          SYNTAX                  SEQUENCE OF IsnsServerEntry
          MAX-ACCESS              not-accessible
          STATUS                  current
          ::= { isnsServerInfo 1 }

      isnsServerEntry             OBJECT-TYPE
          SYNTAX                  IsnsServerEntry
          MAX-ACCESS              not-accessible
          STATUS                  current
          INDEX   { isnsServerIndex }
          ::= { isnsServerTable 1 }

      IsnsServerEntry ::=
          SEQUENCE {
             isnsServerIndex           Unsigned32,
             isnsServerName            SnmpAdminString,
             isnsServerIsnsVersion     Unsigned32,
             isnsServerVendorInfo      SnmpAdminString,





             isnsServerPhysicalIndex   PhysicalIndex,
             isnsServerTcpPort         InetPortNumber,
             isnsServerUdpPort         InetPortNumber,
             isnsServerDiscontinuityTime
                                       TimeStamp,
             isnsServerRole            INTEGER,
             isnsServerDiscoveryMethodsEnabled
                                       IsnsSrvrDiscoveryMethodsType,
             isnsServerDiscoveryMcGroupType
                                       InetAddressType,
             isnsServerDiscoveryMcGroupAddress
                                       InetAddress,
             isnsServerEsiNonResponseThreshold
                                       Unsigned32,
             isnsServerEnableControlNodeMgtScn
                                       TruthValue,
             isnsServerDefaultDdDdsStatus
                                       INTEGER,
             isnsServerUpdateDdDdsSupported
                                       IsnsDdDdsModificationType,
             isnsServerUpdateDdDdsEnabled
                                       IsnsDdDdsModificationType
                   }

      isnsServerIndex             OBJECT-TYPE
          SYNTAX                  Unsigned32 ( 1 .. 4294967295 )
          MAX-ACCESS              not-accessible
          STATUS                  current
          ::= { isnsServerEntry 1 }

      isnsServerName              OBJECT-TYPE
          SYNTAX                  SnmpAdminString
          MAX-ACCESS              read-only
          STATUS                  current
          ::= { isnsServerEntry 2 }

      isnsServerIsnsVersion       OBJECT-TYPE
          SYNTAX                  Unsigned32 ( 0 .. 65535 )





          MAX-ACCESS              read-only
          STATUS                  current
          DEFVAL                  { 1 }
          ::= { isnsServerEntry 3 }

      isnsServerVendorInfo        OBJECT-TYPE
          SYNTAX                  SnmpAdminString
          MAX-ACCESS              read-only
          STATUS                  current
          ::= { isnsServerEntry 4 }

      isnsServerPhysicalIndex     OBJECT-TYPE
          SYNTAX                  PhysicalIndex
          MAX-ACCESS              read-only
          STATUS                  current
          ::= { isnsServerEntry 5 }

      isnsServerTcpPort           OBJECT-TYPE
          SYNTAX                  InetPortNumber





          MAX-ACCESS              read-only
          STATUS                  current
          ::= { isnsServerEntry 6 }

      isnsServerUdpPort           OBJECT-TYPE
          SYNTAX                  InetPortNumber
          MAX-ACCESS              read-only
          STATUS                  current
          ::= { isnsServerEntry 7 }

      isnsServerDiscontinuityTime OBJECT-TYPE
           SYNTAX                 TimeStamp
           MAX-ACCESS             read-only
           STATUS                 current
          ::= { isnsServerEntry 8 }

      isnsServerRole              OBJECT-TYPE
           SYNTAX                 INTEGER { notSet(1),
                                            server(2),
                                            backupServer(3) }
           MAX-ACCESS             read-only
           STATUS                 current
          ::= { isnsServerEntry 9 }

      isnsServerDiscoveryMethodsEnabled  OBJECT-TYPE
          SYNTAX                  IsnsSrvrDiscoveryMethodsType
          MAX-ACCESS              read-only
          STATUS                  current
          ::= { isnsServerEntry 10 }

      isnsServerDiscoveryMcGroupType   OBJECT-TYPE
          SYNTAX                  InetAddressType
          MAX-ACCESS              read-only
          STATUS                  current
          ::= { isnsServerEntry 11 }

      isnsServerDiscoveryMcGroupAddress  OBJECT-TYPE
          SYNTAX                  InetAddress
          MAX-ACCESS              read-only
          STATUS                  current
          ::= { isnsServerEntry 12 }

      isnsServerEsiNonResponseThreshold OBJECT-TYPE
          SYNTAX                  Unsigned32 ( 0 .. 65535 )
          MAX-ACCESS              read-only
          STATUS                  current
          DEFVAL                  { 3 }
          ::= { isnsServerEntry 13 }

      isnsServerEnableControlNodeMgtScn  OBJECT-TYPE
          SYNTAX                  TruthValue
          MAX-ACCESS              read-only
          STATUS                  current
          DEFVAL                  { true }
          ::= { isnsServerEntry 14 }

      isnsServerDefaultDdDdsStatus OBJECT-TYPE
          SYNTAX                  INTEGER { inNoDomain(1),
                                            inDefaultDdAndDds(2) }
          MAX-ACCESS              read-only
          STATUS                  current
          DEFVAL                  { inNoDomain }
          ::= { isnsServerEntry 15 }

      isnsServerUpdateDdDdsSupported OBJECT-TYPE
          SYNTAX                  IsnsDdDdsModificationType
          MAX-ACCESS              read-only
          STATUS                  current
          ::= { isnsServerEntry 16 }






      isnsServerUpdateDdDdsEnabled OBJECT-TYPE
          SYNTAX                  IsnsDdDdsModificationType
          MAX-ACCESS              read-only
          STATUS                  current
          ::= { isnsServerEntry 17 }


      isnsNumObjectsTable         OBJECT-TYPE
          SYNTAX                  SEQUENCE OF
                                      IsnsNumObjectsEntry
          MAX-ACCESS              not-accessible
          STATUS                  current
          ::= { isnsServerInfo 2 }

      isnsNumObjectsEntry         OBJECT-TYPE
          SYNTAX                  IsnsNumObjectsEntry
          MAX-ACCESS              not-accessible
          STATUS                  current
          AUGMENTS { isnsServerEntry }
           ::= { isnsNumObjectsTable 1 }

      IsnsNumObjectsEntry ::= SEQUENCE  {
           isnsNumDds             Gauge32,
           isnsNumDd              Gauge32,
           isnsNumEntities        Gauge32,
           isnsNumPortals         Gauge32,
           isnsNumPortalGroups    Gauge32,
           isnsNumIscsiNodes      Gauge32,
           isnsNumFcPorts         Gauge32,
           isnsNumFcNodes         Gauge32
                                         }






      isnsNumDds                  OBJECT-TYPE
          SYNTAX                  Gauge32 ( 0 .. 4294967295 )
          MAX-ACCESS              read-only
          STATUS                  current
          ::= { isnsNumObjectsEntry 1 }

      isnsNumDd                   OBJECT-TYPE
          SYNTAX                  Gauge32 ( 0 .. 4294967295 )
          MAX-ACCESS              read-only
          STATUS                  current
          ::= { isnsNumObjectsEntry 2 }

      isnsNumEntities             OBJECT-TYPE
          SYNTAX                  Gauge32 ( 0 .. 4294967295 )
          MAX-ACCESS              read-only
          STATUS                  current
          ::= { isnsNumObjectsEntry 3 }

      isnsNumPortals              OBJECT-TYPE
          SYNTAX                  Gauge32 ( 0 .. 4294967295 )
          MAX-ACCESS              read-only
          STATUS                  current
          ::= { isnsNumObjectsEntry 4 }

      isnsNumPortalGroups         OBJECT-TYPE
          SYNTAX                  Gauge32 ( 0 .. 4294967295 )
          MAX-ACCESS              read-only
          STATUS                  current
          ::= { isnsNumObjectsEntry 5 }






      isnsNumIscsiNodes           OBJECT-TYPE
          SYNTAX                  Gauge32 ( 0 .. 4294967295 )
          MAX-ACCESS              read-only
          STATUS                  current
          ::= { isnsNumObjectsEntry 6 }

      isnsNumFcPorts              OBJECT-TYPE
          SYNTAX                  Gauge32 ( 0 .. 4294967295 )
          MAX-ACCESS              read-only
          STATUS                  current
          ::= { isnsNumObjectsEntry 7 }

      isnsNumFcNodes              OBJECT-TYPE
          SYNTAX                  Gauge32 ( 0 .. 4294967295 )
          MAX-ACCESS              read-only
          STATUS                  current
          ::= { isnsNumObjectsEntry 8 }


      isnsControlNodeInfo     OBJECT IDENTIFIER ::=
                                           { isnsServerInfo 3 }


      isnsControlNodeIscsiTable   OBJECT-TYPE
          SYNTAX                  SEQUENCE OF
                                    IsnsControlNodeIscsiEntry
          MAX-ACCESS              not-accessible
          STATUS                  current
          ::= { isnsControlNodeInfo 1 }

      isnsControlNodeIscsiEntry      OBJECT-TYPE
          SYNTAX                  IsnsControlNodeIscsiEntry
          MAX-ACCESS              not-accessible
          STATUS                  current
           INDEX          { isnsServerIndex,
                            isnsControlNodeIscsiNodeIndex }
           ::= { isnsControlNodeIscsiTable 1 }

      IsnsControlNodeIscsiEntry ::= SEQUENCE {
           isnsControlNodeIscsiNodeIndex     IsnsNodeIndexId,
           isnsControlNodeIscsiNodeName      SnmpAdminString,
           isnsControlNodeIscsiIsRegistered  TruthValue,
           isnsControlNodeIscsiRcvMgtSCN     TruthValue
                                          }

      isnsControlNodeIscsiNodeIndex  OBJECT-TYPE
          SYNTAX                  IsnsNodeIndexId
          MAX-ACCESS              not-accessible
          STATUS                  current
           ::= { isnsControlNodeIscsiEntry 1 }

      isnsControlNodeIscsiNodeName   OBJECT-TYPE
          SYNTAX                  SnmpAdminString
          MAX-ACCESS              read-only
          STATUS                  current
           ::= { isnsControlNodeIscsiEntry 2 }

      isnsControlNodeIscsiIsRegistered OBJECT-TYPE
          SYNTAX                  TruthValue
          MAX-ACCESS              read-only





          STATUS                  current
           ::= { isnsControlNodeIscsiEntry 3 }

      isnsControlNodeIscsiRcvMgtSCN  OBJECT-TYPE
          SYNTAX                  TruthValue
          MAX-ACCESS              read-only
          STATUS                  current
           ::= { isnsControlNodeIscsiEntry 4 }


      isnsControlNodeFcPortTable  OBJECT-TYPE
          SYNTAX                  SEQUENCE OF
                                    IsnsControlNodeFcPortEntry
          MAX-ACCESS              not-accessible
          STATUS                  current
          ::= { isnsControlNodeInfo 2 }

      isnsControlNodeFcPortEntry  OBJECT-TYPE
          SYNTAX                  IsnsControlNodeFcPortEntry
          MAX-ACCESS              not-accessible
          STATUS                  current
           INDEX          { isnsServerIndex,
                            isnsControlNodeFcPortWwpn }
           ::= { isnsControlNodeFcPortTable 1 }

      IsnsControlNodeFcPortEntry ::= SEQUENCE  {
           isnsControlNodeFcPortWwpn          FcNameIdOrZero,
           isnsControlNodeFcPortIsRegistered  TruthValue,





           isnsControlNodeFcPortRcvMgtSCN     TruthValue
                                               }

      isnsControlNodeFcPortWwpn   OBJECT-TYPE
          SYNTAX                  FcNameIdOrZero (SIZE(8))
          MAX-ACCESS              not-accessible
          STATUS                  current
           ::= { isnsControlNodeFcPortEntry 1 }

      isnsControlNodeFcPortIsRegistered OBJECT-TYPE
          SYNTAX                  TruthValue
          MAX-ACCESS              read-only
          STATUS                  current
           ::= { isnsControlNodeFcPortEntry 2 }

      isnsControlNodeFcPortRcvMgtSCN OBJECT-TYPE
          SYNTAX                  TruthValue
          MAX-ACCESS              read-only
          STATUS                  current
           ::= { isnsControlNodeFcPortEntry 3 }


      isnsDdsInfo     OBJECT IDENTIFIER ::= { isnsServerInfo 4 }


      isnsDdsTable                OBJECT-TYPE





          SYNTAX                  SEQUENCE OF IsnsDdsEntry
          MAX-ACCESS              not-accessible
          STATUS                  current
          ::= { isnsDdsInfo 1 }

      isnsDdsEntry                OBJECT-TYPE
          SYNTAX                  IsnsDdsEntry
          MAX-ACCESS              not-accessible
          STATUS                  current
          INDEX   { isnsServerIndex, isnsDdsId}
          ::= { isnsDdsTable 1 }

      IsnsDdsEntry ::=
          SEQUENCE {
             isnsDdsId             IsnsDiscoveryDomainSetId,
             isnsDdsSymbolicName   SnmpAdminString,
             isnsDdsStatus         IsnsDdsStatusType
                   }

      isnsDdsId                   OBJECT-TYPE
          SYNTAX                  IsnsDiscoveryDomainSetId
          MAX-ACCESS              not-accessible
          STATUS                  current
          ::= { isnsDdsEntry 1 }

      isnsDdsSymbolicName         OBJECT-TYPE
          SYNTAX                  SnmpAdminString
          MAX-ACCESS              read-only
          STATUS                  current





          ::= { isnsDdsEntry 2 }

      isnsDdsStatus               OBJECT-TYPE
          SYNTAX                  IsnsDdsStatusType
          MAX-ACCESS              read-only
          STATUS                  current
          ::= { isnsDdsEntry 3 }



      isnsDdsMemberTable          OBJECT-TYPE
          SYNTAX                  SEQUENCE OF IsnsDdsMemberEntry
          MAX-ACCESS              not-accessible
          STATUS                  current
          ::= { isnsDdsInfo 2 }


      isnsDdsMemberEntry          OBJECT-TYPE
          SYNTAX                  IsnsDdsMemberEntry
          MAX-ACCESS              not-accessible
          STATUS                  current
          INDEX   { isnsServerIndex,
                    isnsDdsId,
                    isnsDdsMemberDdId }
          ::= { isnsDdsMemberTable 1 }

      IsnsDdsMemberEntry ::=
          SEQUENCE {
             isnsDdsMemberDdId       IsnsDiscoveryDomainId,
             isnsDdsMemberSymbolicName SnmpAdminString





                   }

      isnsDdsMemberDdId           OBJECT-TYPE
          SYNTAX                  IsnsDiscoveryDomainId
          MAX-ACCESS              not-accessible
          STATUS                  current
          ::= { isnsDdsMemberEntry 1 }

      isnsDdsMemberSymbolicName   OBJECT-TYPE
          SYNTAX                  SnmpAdminString
          MAX-ACCESS              read-only
          STATUS                  current
          ::= { isnsDdsMemberEntry 2 }


      isnsDdInfo     OBJECT IDENTIFIER ::= { isnsServerInfo 5 }


      isnsDdTable                 OBJECT-TYPE
          SYNTAX                  SEQUENCE OF IsnsDdEntry
          MAX-ACCESS              not-accessible
          STATUS                  current
          ::= { isnsDdInfo 1 }

      isnsDdEntry                 OBJECT-TYPE
          SYNTAX                  IsnsDdEntry
          MAX-ACCESS              not-accessible
          STATUS                  current
          INDEX   { isnsServerIndex, isnsDdId}
          ::= { isnsDdTable 1 }

      IsnsDdEntry::=
          SEQUENCE {
             isnsDdId             IsnsDiscoveryDomainId,
             isnsDdSymbolicName   SnmpAdminString,
             isnsDdFeatures       IsnsDdFeatureType
                   }

      isnsDdId                    OBJECT-TYPE
          SYNTAX                  IsnsDiscoveryDomainId
          MAX-ACCESS              not-accessible
          STATUS                  current
          ::= { isnsDdEntry 1 }

      isnsDdSymbolicName          OBJECT-TYPE
          SYNTAX                  SnmpAdminString
          MAX-ACCESS              read-only
          STATUS                  current
          ::= { isnsDdEntry 2 }

      isnsDdFeatures              OBJECT-TYPE
          SYNTAX                  IsnsDdFeatureType
          MAX-ACCESS              read-only
          STATUS                  current
          ::= { isnsDdEntry 3 }














      isnsDdIscsiMemberTable      OBJECT-TYPE
          SYNTAX                  SEQUENCE OF
                                    IsnsDdIscsiMemberEntry
          MAX-ACCESS              not-accessible
          STATUS                  current
          ::= { isnsDdInfo 2 }

      isnsDdIscsiMemberEntry      OBJECT-TYPE
          SYNTAX                  IsnsDdIscsiMemberEntry
          MAX-ACCESS              not-accessible
          STATUS                  current
          INDEX   { isnsServerIndex,
                    isnsDdId,
                    isnsDdIscsiMemberIndex }
          ::= { isnsDdIscsiMemberTable 1 }

      IsnsDdIscsiMemberEntry::=
          SEQUENCE {
             isnsDdIscsiMemberIndex   IsnsNodeIndexId,
             isnsDdIscsiMemberName    SnmpAdminString,
             isnsDdIscsiMemberIsRegistered TruthValue
                   }

      isnsDdIscsiMemberIndex      OBJECT-TYPE
          SYNTAX                  IsnsNodeIndexId
          MAX-ACCESS              not-accessible
          STATUS                  current





          ::= { isnsDdIscsiMemberEntry 1 }

      isnsDdIscsiMemberName       OBJECT-TYPE
          SYNTAX                  SnmpAdminString (SIZE (0..223))
          MAX-ACCESS              read-only
          STATUS                  current
          ::= { isnsDdIscsiMemberEntry 2 }

      isnsDdIscsiMemberIsRegistered OBJECT-TYPE
          SYNTAX                  TruthValue
          MAX-ACCESS              read-only
          STATUS                  current
          ::= { isnsDdIscsiMemberEntry 3 }


      isnsDdPortalMemberTable     OBJECT-TYPE
          SYNTAX                  SEQUENCE OF
                                    IsnsDdPortalMemberEntry
          MAX-ACCESS              not-accessible





          STATUS                  current
          ::= { isnsDdInfo 3 }

      isnsDdPortalMemberEntry     OBJECT-TYPE
          SYNTAX                  IsnsDdPortalMemberEntry
          MAX-ACCESS              not-accessible
          STATUS                  current
          INDEX   { isnsServerIndex,
                    isnsDdId,
                    isnsDdPortalMemberIndex }
          ::= { isnsDdPortalMemberTable 1 }

      IsnsDdPortalMemberEntry ::=
          SEQUENCE {
             isnsDdPortalMemberIndex        IsnsPortalIndexId,
             isnsDdPortalMemberAddressType  InetAddressType,
             isnsDdPortalMemberAddress      InetAddress,
             isnsDdPortalMemberPortType     IsnsPortalPortTypeId,
             isnsDdPortalMemberPort         InetPortNumber,
             isnsDdPortalMemberIsRegistered TruthValue
                   }






      isnsDdPortalMemberIndex     OBJECT-TYPE
          SYNTAX                  IsnsPortalIndexId
          MAX-ACCESS              not-accessible
          STATUS                  current
          ::= { isnsDdPortalMemberEntry 1 }

      isnsDdPortalMemberAddressType  OBJECT-TYPE
          SYNTAX                  InetAddressType
          MAX-ACCESS              read-only
          STATUS                  current
          ::= { isnsDdPortalMemberEntry 2 }

      isnsDdPortalMemberAddress   OBJECT-TYPE
          SYNTAX                  InetAddress
          MAX-ACCESS              read-only
          STATUS                  current
          ::= { isnsDdPortalMemberEntry 3 }

      isnsDdPortalMemberPortType  OBJECT-TYPE
          SYNTAX                  IsnsPortalPortTypeId
          MAX-ACCESS              read-only
          STATUS                  current
          ::= { isnsDdPortalMemberEntry 4 }

      isnsDdPortalMemberPort      OBJECT-TYPE
          SYNTAX                  InetPortNumber ( 1 .. 65535 )
          MAX-ACCESS              read-only
          STATUS                  current





          ::= { isnsDdPortalMemberEntry 5 }

      isnsDdPortalMemberIsRegistered OBJECT-TYPE
          SYNTAX                  TruthValue
          MAX-ACCESS              read-only
          STATUS                  current
          ::= { isnsDdPortalMemberEntry 6 }


      isnsDdFcPortMemberTable     OBJECT-TYPE
          SYNTAX                  SEQUENCE OF
                                    IsnsDdFcPortMemberEntry
          MAX-ACCESS              not-accessible
          STATUS                  current
          ::= { isnsDdInfo 4 }

      isnsDdFcPortMemberEntry     OBJECT-TYPE
          SYNTAX                  IsnsDdFcPortMemberEntry
          MAX-ACCESS              not-accessible
          STATUS                  current
          INDEX   { isnsServerIndex,
                    isnsDdId,
                    isnsDdFcPortMemberPortName }
          ::= { isnsDdFcPortMemberTable 1 }






      IsnsDdFcPortMemberEntry ::=
          SEQUENCE {
             isnsDdFcPortMemberPortName FcNameIdOrZero,
             isnsDdFcPortMemberIsRegistered TruthValue
          }

      isnsDdFcPortMemberPortName  OBJECT-TYPE
          SYNTAX                  FcNameIdOrZero (SIZE(8))
          MAX-ACCESS              not-accessible
          STATUS                  current
          ::= { isnsDdFcPortMemberEntry 1 }

      isnsDdFcPortMemberIsRegistered OBJECT-TYPE
          SYNTAX                  TruthValue
          MAX-ACCESS              read-only
          STATUS                  current
          ::= { isnsDdFcPortMemberEntry 2 }


      isnsReg    OBJECT IDENTIFIER ::= { isnsServerInfo 6 }

      isnsRegEntityInfo           OBJECT IDENTIFIER
                                     ::= { isnsReg    1 }


      isnsRegEntityTable          OBJECT-TYPE
          SYNTAX                  SEQUENCE OF IsnsRegEntityEntry
          MAX-ACCESS              not-accessible
          STATUS                  current





          ::= { isnsRegEntityInfo 1 }

      isnsRegEntityEntry          OBJECT-TYPE
          SYNTAX                  IsnsRegEntityEntry
          MAX-ACCESS              not-accessible
          STATUS                  current
          INDEX   { isnsServerIndex,
                    isnsRegEntityIndex }
          ::= { isnsRegEntityTable 1 }

      IsnsRegEntityEntry ::=
          SEQUENCE {
             isnsRegEntityIndex          IsnsEntityIndexIdOrZero,
             isnsRegEntityEID            SnmpAdminString,
             isnsRegEntityProtocol       Unsigned32,
             isnsRegEntityManagementAddressType
                                         InetAddressType,
             isnsRegEntityManagementAddress
                                         InetAddress,
             isnsRegEntityTimestamp      TimeStamp,
             isnsRegEntityVersionMin     Unsigned32,
             isnsRegEntityVersionMax     Unsigned32,
             isnsRegEntityRegistrationPeriod
                                         Unsigned32
                  }

      isnsRegEntityIndex          OBJECT-TYPE
          SYNTAX                  IsnsEntityIndexIdOrZero
                                         ( 1 .. 4294967295 )
          MAX-ACCESS              not-accessible
          STATUS                  current





          ::= { isnsRegEntityEntry 1 }

      isnsRegEntityEID            OBJECT-TYPE
          SYNTAX                  SnmpAdminString
          MAX-ACCESS              read-only
          STATUS                  current
          ::= { isnsRegEntityEntry 2 }

      isnsRegEntityProtocol       OBJECT-TYPE
          SYNTAX                  Unsigned32 ( 1 .. 4294967295 )
          MAX-ACCESS              read-only
          STATUS                  current
          ::= { isnsRegEntityEntry 3 }

      isnsRegEntityManagementAddressType OBJECT-TYPE
          SYNTAX                  InetAddressType
          MAX-ACCESS              read-only
          STATUS                  current
          ::= { isnsRegEntityEntry 4 }






      isnsRegEntityManagementAddress OBJECT-TYPE
          SYNTAX                  InetAddress
          MAX-ACCESS              read-only
          STATUS                  current
          ::= { isnsRegEntityEntry 5 }

      isnsRegEntityTimestamp      OBJECT-TYPE
          SYNTAX                  TimeStamp
          MAX-ACCESS              read-only
          STATUS                  current
          ::= { isnsRegEntityEntry 6 }

      isnsRegEntityVersionMin     OBJECT-TYPE
          SYNTAX                  Unsigned32 ( 0 .. 254 | 255 )
          MAX-ACCESS              read-only
          STATUS                  current
          ::= { isnsRegEntityEntry 7 }

      isnsRegEntityVersionMax     OBJECT-TYPE
          SYNTAX                  Unsigned32 ( 0 .. 254 | 255 )
          MAX-ACCESS              read-only
          STATUS                  current
          ::= { isnsRegEntityEntry 8 }

      isnsRegEntityRegistrationPeriod OBJECT-TYPE
          SYNTAX                  Unsigned32 ( 0 .. 4294967295 )
          UNITS                   "seconds"
          MAX-ACCESS              read-only
          STATUS                  current
          ::= { isnsRegEntityEntry 9 }


      isnsRegEntityNumObjectsTable    OBJECT-TYPE
          SYNTAX                  SEQUENCE OF
                                    IsnsRegEntityNumObjectsEntry
          MAX-ACCESS              not-accessible
          STATUS                  current
          ::= { isnsRegEntityInfo 2 }

      isnsRegEntityNumObjectsEntry    OBJECT-TYPE
          SYNTAX                  IsnsRegEntityNumObjectsEntry
          MAX-ACCESS              not-accessible
          STATUS                  current
          INDEX   { isnsServerIndex,
                    isnsRegEntityIndex }





          ::= { isnsRegEntityNumObjectsTable 1 }

      IsnsRegEntityNumObjectsEntry ::=
          SEQUENCE {
             isnsRegEntityInfoNumPortals      Gauge32,
             isnsRegEntityInfoNumPortalGroups Gauge32,
             isnsRegEntityInfoNumIscsiNodes   Gauge32,
             isnsRegEntityInfoNumFcPorts      Gauge32,
             isnsRegEntityInfoNumFcNodes      Gauge32
                  }

      isnsRegEntityInfoNumPortals OBJECT-TYPE
          SYNTAX                  Gauge32 ( 0 .. 4294967295 )
          MAX-ACCESS              read-only
          STATUS                  current
          ::= { isnsRegEntityNumObjectsEntry 1 }

      isnsRegEntityInfoNumPortalGroups OBJECT-TYPE
          SYNTAX                  Gauge32 ( 0 .. 4294967295 )
          MAX-ACCESS              read-only
          STATUS                  current
          ::= { isnsRegEntityNumObjectsEntry 2 }

      isnsRegEntityInfoNumIscsiNodes OBJECT-TYPE
          SYNTAX                  Gauge32 ( 0 .. 4294967295 )
          MAX-ACCESS              read-only
          STATUS                  current
          ::= { isnsRegEntityNumObjectsEntry 3 }

      isnsRegEntityInfoNumFcPorts OBJECT-TYPE
          SYNTAX                  Gauge32 ( 0 .. 4294967295 )
          MAX-ACCESS              read-only
          STATUS                  current
          ::= { isnsRegEntityNumObjectsEntry 4 }

      isnsRegEntityInfoNumFcNodes OBJECT-TYPE
          SYNTAX                  Gauge32 ( 0 .. 4294967295 )
          MAX-ACCESS              read-only
          STATUS                  current





          ::= { isnsRegEntityNumObjectsEntry 5 }


      isnsRegPortalInfo           OBJECT IDENTIFIER
                                     ::= { isnsReg  2 }


      isnsRegPortalTable          OBJECT-TYPE
          SYNTAX                  SEQUENCE OF IsnsRegPortalEntry
          MAX-ACCESS              not-accessible
          STATUS                  current
          ::= { isnsRegPortalInfo 1 }

      isnsRegPortalEntry          OBJECT-TYPE
          SYNTAX                  IsnsRegPortalEntry
          MAX-ACCESS              not-accessible
          STATUS                  current
          INDEX   { isnsServerIndex,
                    isnsRegEntityIndex,
                    isnsRegPortalPortalIndex }
          ::= { isnsRegPortalTable 1 }

      IsnsRegPortalEntry ::=
          SEQUENCE {
             isnsRegPortalPortalIndex    IsnsPortalIndexId,
             isnsRegPortalAddressType    InetAddressType,
             isnsRegPortalAddress        InetAddress,
             isnsRegPortalPortType       IsnsPortalPortTypeId,
             isnsRegPortalPort           InetPortNumber,
             isnsRegPortalSymbolicName   SnmpAdminString,
             isnsRegPortalEsiInterval    Unsigned32,
             isnsRegPortalEsiPortType    IsnsPortalPortTypeId,





             isnsRegPortalEsiPort        InetPortNumber,
             isnsRegPortalScnPortType    IsnsPortalPortTypeId,
             isnsRegPortalScnPort        InetPortNumber,
             isnsRegPortalSecurityInfo   IsnsPortalSecurityType
                  }

      isnsRegPortalPortalIndex    OBJECT-TYPE
          SYNTAX                  IsnsPortalIndexId
          MAX-ACCESS              not-accessible
          STATUS                  current
          ::= { isnsRegPortalEntry 1 }

      isnsRegPortalAddressType    OBJECT-TYPE
          SYNTAX                  InetAddressType
          MAX-ACCESS              read-only
          STATUS                  current
          ::= { isnsRegPortalEntry 2 }

      isnsRegPortalAddress        OBJECT-TYPE
          SYNTAX                  InetAddress
          MAX-ACCESS              read-only
          STATUS                  current
          ::= { isnsRegPortalEntry 3 }

      isnsRegPortalPortType       OBJECT-TYPE
          SYNTAX                  IsnsPortalPortTypeId
          MAX-ACCESS              read-only
          STATUS                  current
          ::= { isnsRegPortalEntry 4 }






      isnsRegPortalPort           OBJECT-TYPE
          SYNTAX                  InetPortNumber ( 1 .. 65535 )
          MAX-ACCESS              read-only
          STATUS                  current
          ::= { isnsRegPortalEntry 5 }

      isnsRegPortalSymbolicName   OBJECT-TYPE
          SYNTAX                  SnmpAdminString
          MAX-ACCESS              read-only
          STATUS                  current
          ::= { isnsRegPortalEntry 6 }

      isnsRegPortalEsiInterval    OBJECT-TYPE
          SYNTAX                  Unsigned32 ( 0 .. 65535 )
          UNITS                   "seconds"
          MAX-ACCESS              read-only
          STATUS                  current
          ::= { isnsRegPortalEntry 7 }

      isnsRegPortalEsiPortType    OBJECT-TYPE
          SYNTAX                  IsnsPortalPortTypeId
          MAX-ACCESS              read-only
          STATUS                  current
          ::= { isnsRegPortalEntry 8 }

      isnsRegPortalEsiPort        OBJECT-TYPE
          SYNTAX                  InetPortNumber





          MAX-ACCESS              read-only
          STATUS                  current
          ::= { isnsRegPortalEntry 9 }

      isnsRegPortalScnPortType    OBJECT-TYPE
          SYNTAX                  IsnsPortalPortTypeId
          MAX-ACCESS              read-only
          STATUS                  current
          ::= { isnsRegPortalEntry 10 }

      isnsRegPortalScnPort        OBJECT-TYPE
          SYNTAX                  InetPortNumber
          MAX-ACCESS              read-only
          STATUS                  current
          ::= { isnsRegPortalEntry 11 }

      isnsRegPortalSecurityInfo   OBJECT-TYPE
          SYNTAX                  IsnsPortalSecurityType
          MAX-ACCESS              read-only
          STATUS                  current
          ::= { isnsRegPortalEntry 12 }









      isnsRegPortalGroupInfo      OBJECT IDENTIFIER
                                     ::= { isnsReg  3 }


      isnsRegPgTable              OBJECT-TYPE
          SYNTAX                  SEQUENCE OF IsnsRegPgEntry
          MAX-ACCESS              not-accessible
          STATUS                  current
          ::= { isnsRegPortalGroupInfo 1 }

      isnsRegPgEntry              OBJECT-TYPE
          SYNTAX                  IsnsRegPgEntry
          MAX-ACCESS              not-accessible
          STATUS                  current
          INDEX   { isnsServerIndex,
                    isnsRegEntityIndex,
                    isnsRegPgIndex }
          ::= { isnsRegPgTable 1 }

      IsnsRegPgEntry ::=
          SEQUENCE {
             isnsRegPgIndex              IsnsPortalGroupIndexId,
             isnsRegPgIscsiNodeIndex     IsnsNodeIndexId,
             isnsRegPgIscsiName          SnmpAdminString,
             isnsRegPgPortalPortalIndex  IsnsPortalIndexId,
             isnsRegPgPortalAddressType  InetAddressType,
             isnsRegPgPortalAddress      InetAddress,
             isnsRegPgPortalPortType     IsnsPortalPortTypeId,
             isnsRegPgPortalPort         InetPortNumber,
             isnsRegPgPGT                IsnsPortalGroupTagIdOrNull
                   }






      isnsRegPgIndex              OBJECT-TYPE
          SYNTAX                  IsnsPortalGroupIndexId
          MAX-ACCESS              not-accessible
          STATUS                  current
          ::= { isnsRegPgEntry 1 }

      isnsRegPgIscsiNodeIndex     OBJECT-TYPE
          SYNTAX                  IsnsNodeIndexId
          MAX-ACCESS              read-only
          STATUS                  current
          ::= { isnsRegPgEntry 2 }

      isnsRegPgIscsiName          OBJECT-TYPE
          SYNTAX                  SnmpAdminString (SIZE (0..223))
          MAX-ACCESS              read-only
          STATUS                  current
          ::= { isnsRegPgEntry 3 }

      isnsRegPgPortalPortalIndex  OBJECT-TYPE
          SYNTAX                  IsnsPortalIndexId
          MAX-ACCESS              read-only
          STATUS                  current
          ::= { isnsRegPgEntry 4 }

      isnsRegPgPortalAddressType  OBJECT-TYPE





          SYNTAX                  InetAddressType
          MAX-ACCESS              read-only
          STATUS                  current
          ::= { isnsRegPgEntry 5 }

      isnsRegPgPortalAddress      OBJECT-TYPE
          SYNTAX                  InetAddress
          MAX-ACCESS              read-only
          STATUS                  current
          ::= { isnsRegPgEntry 6 }

      isnsRegPgPortalPortType     OBJECT-TYPE
          SYNTAX                  IsnsPortalPortTypeId
          MAX-ACCESS              read-only
          STATUS                  current
          ::= { isnsRegPgEntry 7 }

      isnsRegPgPortalPort         OBJECT-TYPE
          SYNTAX                  InetPortNumber ( 1 .. 65535 )
          MAX-ACCESS              read-only
          STATUS                  current
          ::= { isnsRegPgEntry 8 }

      isnsRegPgPGT                OBJECT-TYPE
          SYNTAX                  IsnsPortalGroupTagIdOrNull
          MAX-ACCESS              read-only
          STATUS                  current





          ::= { isnsRegPgEntry 9 }


      isnsRegIscsiNodeInfo  OBJECT IDENTIFIER ::= { isnsReg  4 }


      isnsRegIscsiNodeTable       OBJECT-TYPE
          SYNTAX                  SEQUENCE OF IsnsRegIscsiNodeEntry
          MAX-ACCESS              not-accessible
          STATUS                  current
          ::= { isnsRegIscsiNodeInfo 1 }

      isnsRegIscsiNodeEntry       OBJECT-TYPE
          SYNTAX                  IsnsRegIscsiNodeEntry
          MAX-ACCESS              not-accessible
          STATUS                  current
          INDEX { isnsServerIndex,
                  isnsRegEntityIndex,
                  isnsRegIscsiNodeIndex }
          ::= { isnsRegIscsiNodeTable 1 }

      IsnsRegIscsiNodeEntry ::= SEQUENCE {





          isnsRegIscsiNodeIndex          IsnsNodeIndexId,
          isnsRegIscsiNodeName           SnmpAdminString,
          isnsRegIscsiNodeType           IsnsIscsiNodeType,
          isnsRegIscsiNodeAlias          SnmpAdminString,
          isnsRegIscsiNodeScnTypes       IsnsIscsiScnType,
          isnsRegIscsiNodeWwnToken       FcNameIdOrZero,
          isnsRegIscsiNodeAuthMethod     SnmpAdminString
                                       }

      isnsRegIscsiNodeIndex       OBJECT-TYPE
          SYNTAX                  IsnsNodeIndexId
          MAX-ACCESS              not-accessible
          STATUS                  current
          ::= { isnsRegIscsiNodeEntry 1 }

      isnsRegIscsiNodeName        OBJECT-TYPE
          SYNTAX                  SnmpAdminString (SIZE (0..223))
          MAX-ACCESS              read-only
          STATUS                  current
          ::= { isnsRegIscsiNodeEntry 2 }

      isnsRegIscsiNodeType        OBJECT-TYPE
          SYNTAX                  IsnsIscsiNodeType
          MAX-ACCESS              read-only
          STATUS                  current
          ::= { isnsRegIscsiNodeEntry 3 }

      isnsRegIscsiNodeAlias       OBJECT-TYPE
          SYNTAX                  SnmpAdminString
          MAX-ACCESS              read-only
          STATUS                  current





          ::= { isnsRegIscsiNodeEntry 4 }

      isnsRegIscsiNodeScnTypes    OBJECT-TYPE
          SYNTAX                  IsnsIscsiScnType
          MAX-ACCESS              read-only
          STATUS                  current
          ::= { isnsRegIscsiNodeEntry 5 }

      isnsRegIscsiNodeWwnToken    OBJECT-TYPE
          SYNTAX                  FcNameIdOrZero
          MAX-ACCESS              read-only
          STATUS                  current
          ::= { isnsRegIscsiNodeEntry 6 }

      isnsRegIscsiNodeAuthMethod  OBJECT-TYPE
          SYNTAX                  SnmpAdminString
          MAX-ACCESS              read-only
          STATUS                  current
          ::= { isnsRegIscsiNodeEntry 7 }


      isnsRegFcNodeInfo     OBJECT IDENTIFIER ::= { isnsReg  5 }







      isnsRegFcNodeTable          OBJECT-TYPE
          SYNTAX                  SEQUENCE OF IsnsRegFcNodeEntry
          MAX-ACCESS              not-accessible
          STATUS                  current
          ::= { isnsRegFcNodeInfo 1 }

      isnsRegFcNodeEntry          OBJECT-TYPE
          SYNTAX                  IsnsRegFcNodeEntry
          MAX-ACCESS              not-accessible
          STATUS                  current
          INDEX { isnsServerIndex,
                   isnsRegFcNodeWwnn }
          ::= { isnsRegFcNodeTable 1 }

      IsnsRegFcNodeEntry ::= SEQUENCE {
          isnsRegFcNodeWwnn           FcNameIdOrZero,
          isnsRegFcNodeSymbolicName   SnmpAdminString,
          isnsRegFcNodeAddressType    InetAddressType,
          isnsRegFcNodeAddress        InetAddress,
          isnsRegFcNodeIPA            OCTET STRING,
          isnsRegFcNodeProxyIscsiName SnmpAdminString,
          isnsRegFcNodeNumFcPorts     Gauge32
                                      }

      isnsRegFcNodeWwnn           OBJECT-TYPE
          SYNTAX                  FcNameIdOrZero (SIZE(8))
          MAX-ACCESS              not-accessible
          STATUS                  current
          ::= { isnsRegFcNodeEntry 1 }

      isnsRegFcNodeSymbolicName   OBJECT-TYPE
          SYNTAX                  SnmpAdminString





          MAX-ACCESS              read-only
          STATUS                  current
          ::= { isnsRegFcNodeEntry 2 }

      isnsRegFcNodeAddressType    OBJECT-TYPE
          SYNTAX                  InetAddressType
          MAX-ACCESS              read-only
          STATUS                  current
          ::= { isnsRegFcNodeEntry 3 }

      isnsRegFcNodeAddress        OBJECT-TYPE
          SYNTAX                  InetAddress
          MAX-ACCESS              read-only
          STATUS                  current
          ::= { isnsRegFcNodeEntry 4 }

      isnsRegFcNodeIPA            OBJECT-TYPE
          SYNTAX                  OCTET STRING (SIZE(8))
          MAX-ACCESS              read-only
          STATUS                  current
          ::= { isnsRegFcNodeEntry 5 }

      isnsRegFcNodeProxyIscsiName OBJECT-TYPE
          SYNTAX                  SnmpAdminString (SIZE (0..223))
          MAX-ACCESS              read-only





          STATUS                  current
          ::= { isnsRegFcNodeEntry 6 }

      isnsRegFcNodeNumFcPorts     OBJECT-TYPE
          SYNTAX                  Gauge32 ( 0 .. 4294967295 )
          MAX-ACCESS              read-only
          STATUS                  current
          ::= { isnsRegFcNodeEntry 7 }


      isnsRegFcPortTable          OBJECT-TYPE
          SYNTAX                  SEQUENCE OF IsnsRegFcPortEntry
          MAX-ACCESS              not-accessible
          STATUS                  current
          ::= { isnsRegFcNodeInfo 2 }

      isnsRegFcPortEntry          OBJECT-TYPE
          SYNTAX                   IsnsRegFcPortEntry
          MAX-ACCESS              not-accessible
          STATUS                  current
          INDEX { isnsServerIndex,
                  isnsRegEntityIndex,
                  isnsRegFcPortWwpn }
          ::= { isnsRegFcPortTable 1 }

      IsnsRegFcPortEntry ::= SEQUENCE {
          isnsRegFcPortWwpn              FcNameIdOrZero,





          isnsRegFcPortID                FcAddressIdOrZero,
          isnsRegFcPortType              Unsigned32,
          isnsRegFcPortSymbolicName      SnmpAdminString,
          isnsRegFcPortFabricPortWwn     FcNameIdOrZero,
          isnsRegFcPortHA                FcAddressIdOrZero,
          isnsRegFcPortAddressType       InetAddressType,
          isnsRegFcPortAddress           InetAddress,
          isnsRegFcPortFcCos             IsnsFcClassOfServiceType,
          isnsRegFcPortFc4Types          OCTET STRING,
          isnsRegFcPortFc4Descr          SnmpAdminString,
          isnsRegFcPortFc4Features       OCTET STRING,
          isnsRegFcPortScnTypes          IsnsIfcpScnType,
          isnsRegFcPortRole              IsnsFcPortRoleType,
          isnsRegFcPortFcNodeWwnn        FcNameIdOrZero,
          isnsRegFcPortPpnWwn            FcNameIdOrZero
                                      }

      isnsRegFcPortWwpn           OBJECT-TYPE
          SYNTAX                  FcNameIdOrZero (SIZE(8))
          MAX-ACCESS              not-accessible
          STATUS                  current
          ::= { isnsRegFcPortEntry 1 }

      isnsRegFcPortID             OBJECT-TYPE
          SYNTAX                  FcAddressIdOrZero
          MAX-ACCESS              read-only
          STATUS                  current
          ::= { isnsRegFcPortEntry 2 }

      isnsRegFcPortType           OBJECT-TYPE
          SYNTAX                  Unsigned32 ( 0 .. 65535 )
          MAX-ACCESS              read-only
          STATUS                  current
          ::= { isnsRegFcPortEntry 3 }

      isnsRegFcPortSymbolicName OBJECT-TYPE
          SYNTAX                SnmpAdminString
          MAX-ACCESS            read-only
          STATUS                current
          ::= { isnsRegFcPortEntry 4 }

      isnsRegFcPortFabricPortWwn  OBJECT-TYPE
          SYNTAX                  FcNameIdOrZero
          MAX-ACCESS              read-only
          STATUS                  current
         ::= { isnsRegFcPortEntry 5 }

      isnsRegFcPortHA             OBJECT-TYPE
          SYNTAX                  FcAddressIdOrZero
          MAX-ACCESS              read-only
          STATUS                  current
          ::= { isnsRegFcPortEntry 6 }

      isnsRegFcPortAddressType    OBJECT-TYPE





          SYNTAX                  InetAddressType
          MAX-ACCESS              read-only
          STATUS                  current
          ::= { isnsRegFcPortEntry 7 }

      isnsRegFcPortAddress        OBJECT-TYPE
          SYNTAX                  InetAddress
          MAX-ACCESS              read-only
          STATUS                  current
          ::= { isnsRegFcPortEntry 8 }

      isnsRegFcPortFcCos          OBJECT-TYPE
          SYNTAX                  IsnsFcClassOfServiceType
          MAX-ACCESS              read-only
          STATUS                  current
          ::= { isnsRegFcPortEntry 9 }

      isnsRegFcPortFc4Types       OBJECT-TYPE
          SYNTAX                  OCTET STRING (SIZE (32))
          MAX-ACCESS              read-only
          STATUS                  current
          ::= { isnsRegFcPortEntry 10 }

      isnsRegFcPortFc4Descr       OBJECT-TYPE
          SYNTAX                  SnmpAdminString (SIZE(4..255))
          MAX-ACCESS              read-only
          STATUS                  current
         ::= { isnsRegFcPortEntry 11 }

      isnsRegFcPortFc4Features    OBJECT-TYPE
          SYNTAX                  OCTET STRING (SIZE (128))
          MAX-ACCESS              read-only
          STATUS                  current
          ::= { isnsRegFcPortEntry 12 }

      isnsRegFcPortScnTypes       OBJECT-TYPE
          SYNTAX                  IsnsIfcpScnType
          MAX-ACCESS              read-only
          STATUS                  current
          ::= { isnsRegFcPortEntry 13 }

      isnsRegFcPortRole           OBJECT-TYPE
          SYNTAX                  IsnsFcPortRoleType
          MAX-ACCESS              read-only
          STATUS                  current
          ::= { isnsRegFcPortEntry 14 }

      isnsRegFcPortFcNodeWwnn     OBJECT-TYPE
          SYNTAX                  FcNameIdOrZero
          MAX-ACCESS              read-only
          STATUS                  current
          ::= { isnsRegFcPortEntry 15 }






      isnsRegFcPortPpnWwn         OBJECT-TYPE
          SYNTAX                  FcNameIdOrZero
          MAX-ACCESS              read-only
          STATUS                  current
          ::= { isnsRegFcPortEntry 16 }


      isnsRegFcNodePortTable      OBJECT-TYPE
          SYNTAX                  SEQUENCE OF
                                    IsnsRegFcNodePortEntry
          MAX-ACCESS              not-accessible
          STATUS                  current
          ::= { isnsRegFcNodeInfo 3 }

      isnsRegFcNodePortEntry      OBJECT-TYPE
          SYNTAX                  IsnsRegFcNodePortEntry
          MAX-ACCESS              not-accessible
          STATUS                  current
          INDEX { isnsServerIndex,
                  isnsRegFcNodeWwnn,
                  isnsRegFcPortWwpn }
          ::= { isnsRegFcNodePortTable 1 }

      IsnsRegFcNodePortEntry ::= SEQUENCE {
              isnsRegFcNodePortEntityIndex IsnsEntityIndexIdOrZero
                                          }






      isnsRegFcNodePortEntityIndex OBJECT-TYPE
          SYNTAX                  IsnsEntityIndexIdOrZero
          MAX-ACCESS              read-only
          STATUS                  current
          ::= { isnsRegFcNodePortEntry 1 }


      isnsNotificationsInfo        OBJECT IDENTIFIER
                                        ::= { isnsObjects 2 }

      isnsInstanceInfo            OBJECT-TYPE
          SYNTAX                  SnmpAdminString
          MAX-ACCESS              accessible-for-notify
          STATUS                  current
          ::= { isnsNotificationsInfo 1 }

      isnsAddressNotificationType OBJECT-TYPE
          SYNTAX                  InetAddressType
          MAX-ACCESS              accessible-for-notify
          STATUS                  current
          ::= { isnsNotificationsInfo 2 }

      isnsAddressNotification     OBJECT-TYPE
          SYNTAX                  InetAddress
          MAX-ACCESS              accessible-for-notify
          STATUS                  current
          ::= { isnsNotificationsInfo 3 }

      isnsTcpPortNotification     OBJECT-TYPE
          SYNTAX                  InetPortNumber
          MAX-ACCESS              accessible-for-notify
          STATUS                  current
          ::= { isnsNotificationsInfo 4 }

      isnsUdpPortNotification     OBJECT-TYPE
          SYNTAX                  InetPortNumber
          MAX-ACCESS              accessible-for-notify
          STATUS                  current
          ::= { isnsNotificationsInfo 5 }


      isnsServerStart             NOTIFICATION-TYPE
          OBJECTS {
              isnsInstanceInfo,
              isnsAddressNotificationType,
              isnsAddressNotification,
              isnsTcpPortNotification,
              isnsUdpPortNotification
                  }
          STATUS                  current
          ::= { isnsNotifications 1 }

      isnsServerShutdown          NOTIFICATION-TYPE





          OBJECTS {
              isnsInstanceInfo,
              isnsAddressNotificationType,
              isnsAddressNotification,
              isnsTcpPortNotification,
              isnsUdpPortNotification
                  }
          STATUS                  current
          ::= { isnsNotifications 2 }


      isnsCompliances OBJECT IDENTIFIER ::= { isnsConformance 1 }

      isnsIscsiServerCompliance MODULE-COMPLIANCE
          STATUS                  current
          MODULE       -- this module
          MANDATORY-GROUPS {
              isnsServerAttributesGroup,
              isnsServerIscsiControlNodeGroup,
              isnsServerIscsiDdsDdObjGroup,
              isnsServerRegIscsiObjGroup,
              isnsServerNumObjectsGroup,
              isnsNotificationsObjGroup,
              isnsServerNotificationGroup
                           }
          OBJECT isnsServerDiscoveryMcGroupType
          SYNTAX InetAddressType { unknown(0), ipv4(1), ipv6(2),
                                     ipv4z(3), ipv6z(4) }






          OBJECT isnsServerDiscoveryMcGroupAddress
          SYNTAX InetAddress (SIZE (0 | 4 | 8 | 16 | 20 ))

          OBJECT isnsDdPortalMemberAddressType
          SYNTAX InetAddressType { unknown(0), ipv4(1), ipv6(2),
                                     ipv4z(3), ipv6z(4) }

          OBJECT isnsDdPortalMemberAddress
          SYNTAX InetAddress (SIZE (0 | 4 | 8 | 16 | 20 ))

          OBJECT isnsRegEntityManagementAddressType
          SYNTAX InetAddressType { unknown(0), ipv4(1), ipv6(2),
                                     ipv4z(3), ipv6z(4) }

          OBJECT isnsRegEntityManagementAddress
          SYNTAX InetAddress (SIZE (0 | 4 | 8 | 16 | 20 ))

          OBJECT isnsRegPortalAddressType
          SYNTAX InetAddressType { unknown(0), ipv4(1), ipv6(2),
                                     ipv4z(3), ipv6z(4) }

          OBJECT isnsRegPortalAddress
          SYNTAX InetAddress (SIZE (0 | 4 | 8 | 16 | 20 ))

          OBJECT isnsRegPgPortalAddressType
          SYNTAX InetAddressType { unknown(0), ipv4(1), ipv6(2),
                                     ipv4z(3), ipv6z(4) }






          OBJECT isnsRegPgPortalAddress
          SYNTAX InetAddress (SIZE (0 | 4 | 8 | 16 | 20 ))

          OBJECT isnsAddressNotificationType
          SYNTAX InetAddressType { unknown(0), ipv4(1), ipv6(2),
                                     ipv4z(3), ipv6z(4) }

          OBJECT isnsAddressNotification
          SYNTAX InetAddress (SIZE (0 | 4 | 8 | 16 | 20 ))
          ::= { isnsCompliances 1 }

      isnsIfcpServerCompliance MODULE-COMPLIANCE
          STATUS                  current
          MODULE       -- this module
          MANDATORY-GROUPS {
              isnsServerAttributesGroup,
              isnsServerIfcpPortControlNodeGroup,
              isnsServerIfcpDdsDdObjGroup,
              isnsServerRegIfcpObjGroup,
              isnsServerNumObjectsGroup,
              isnsNotificationsObjGroup,
              isnsServerNotificationGroup
                           }
          OBJECT isnsServerDiscoveryMcGroupType
          SYNTAX InetAddressType { unknown(0), ipv4(1), ipv6(2),
                                     ipv4z(3), ipv6z(4) }

          OBJECT isnsServerDiscoveryMcGroupAddress
          SYNTAX InetAddress (SIZE (0 | 4 | 8 | 16 | 20 ))






          OBJECT isnsDdPortalMemberAddressType
          SYNTAX InetAddressType { unknown(0), ipv4(1), ipv6(2),
                                     ipv4z(3), ipv6z(4) }

          OBJECT isnsDdPortalMemberAddress
          SYNTAX InetAddress (SIZE (0 | 4 | 8 | 16 | 20 ))

          OBJECT isnsRegEntityManagementAddressType
          SYNTAX InetAddressType { unknown(0), ipv4(1), ipv6(2),
                                     ipv4z(3), ipv6z(4) }

          OBJECT isnsRegEntityManagementAddress
          SYNTAX InetAddress (SIZE (0 | 4 | 8 | 16 | 20 ))

          OBJECT isnsRegPortalAddressType
          SYNTAX InetAddressType { unknown(0), ipv4(1), ipv6(2),
                                     ipv4z(3), ipv6z(4) }

          OBJECT isnsRegPortalAddress
          SYNTAX InetAddress (SIZE (0 | 4 | 8 | 16 | 20 ))

          OBJECT isnsRegFcNodeAddressType
          SYNTAX InetAddressType { unknown(0), ipv4(1), ipv6(2),
                                     ipv4z(3), ipv6z(4) }

          OBJECT isnsRegFcNodeAddress
          SYNTAX InetAddress (SIZE (0 | 4 | 8 | 16 | 20 ))

          OBJECT isnsRegFcPortAddressType
          SYNTAX InetAddressType { unknown(0), ipv4(1), ipv6(2),
                                     ipv4z(3), ipv6z(4) }

          OBJECT isnsRegFcPortAddress
          SYNTAX InetAddress (SIZE (0 | 4 | 8 | 16 | 20 ))

          OBJECT isnsAddressNotificationType
          SYNTAX InetAddressType { unknown(0), ipv4(1), ipv6(2),
                                     ipv4z(3), ipv6z(4) }

          OBJECT isnsAddressNotification
          SYNTAX InetAddress (SIZE (0 | 4 | 8 | 16 | 20 ))
          ::= { isnsCompliances 2 }

   isnsGroups OBJECT IDENTIFIER ::= { isnsConformance 2 }

      isnsServerAttributesGroup      OBJECT-GROUP
          OBJECTS {
             isnsServerName,
             isnsServerIsnsVersion,
             isnsServerVendorInfo,
             isnsServerPhysicalIndex,
             isnsServerTcpPort,
             isnsServerUdpPort,
             isnsServerDiscontinuityTime,
             isnsServerRole,
             isnsServerDiscoveryMethodsEnabled,





             isnsServerDiscoveryMcGroupType,
             isnsServerDiscoveryMcGroupAddress,
             isnsServerEsiNonResponseThreshold,
             isnsServerEnableControlNodeMgtScn,
             isnsServerDefaultDdDdsStatus,
             isnsServerUpdateDdDdsSupported,
             isnsServerUpdateDdDdsEnabled
                  }
          STATUS                  current
             ::= { isnsGroups 1 }

      isnsServerNumObjectsGroup      OBJECT-GROUP
          OBJECTS {
             isnsNumDds,
             isnsNumDd,
             isnsNumEntities,
             isnsNumPortals,
             isnsNumPortalGroups,
             isnsNumIscsiNodes,
             isnsNumFcPorts,
             isnsNumFcNodes,
             isnsRegEntityInfoNumPortals,
             isnsRegEntityInfoNumPortalGroups,
             isnsRegEntityInfoNumIscsiNodes,
             isnsRegEntityInfoNumFcPorts,
             isnsRegEntityInfoNumFcNodes
                  }
          STATUS                  current
             ::= { isnsGroups 2 }

      isnsServerIscsiControlNodeGroup    OBJECT-GROUP
          OBJECTS {
             isnsControlNodeIscsiNodeName,
             isnsControlNodeIscsiIsRegistered,
             isnsControlNodeIscsiRcvMgtSCN
                  }
          STATUS                  current
             ::= { isnsGroups 3 }






      isnsServerIfcpPortControlNodeGroup   OBJECT-GROUP
          OBJECTS {
             isnsControlNodeFcPortIsRegistered,
             isnsControlNodeFcPortRcvMgtSCN
                  }
          STATUS                  current
             ::= { isnsGroups 4 }

      isnsServerIscsiDdsDdObjGroup   OBJECT-GROUP
          OBJECTS {
             isnsDdsSymbolicName,
             isnsDdsStatus,
             isnsDdsMemberSymbolicName,
             isnsDdSymbolicName,
             isnsDdFeatures,
             isnsDdIscsiMemberName,
             isnsDdIscsiMemberIsRegistered,
             isnsDdPortalMemberAddressType,
             isnsDdPortalMemberAddress,
             isnsDdPortalMemberPortType,
             isnsDdPortalMemberPort,
             isnsDdPortalMemberIsRegistered
                  }
          STATUS                  current
             ::= { isnsGroups 5 }

      isnsServerIfcpDdsDdObjGroup    OBJECT-GROUP
          OBJECTS {
             isnsDdsSymbolicName,
             isnsDdsStatus,
             isnsDdSymbolicName,
             isnsDdFeatures,
             isnsDdPortalMemberAddressType,
             isnsDdPortalMemberAddress,
             isnsDdPortalMemberPortType,
             isnsDdPortalMemberPort,
             isnsDdPortalMemberIsRegistered,
             isnsDdFcPortMemberIsRegistered
                  }
          STATUS                  current
             ::= { isnsGroups 6 }






      isnsServerRegIscsiObjGroup   OBJECT-GROUP
          OBJECTS {
             isnsRegEntityEID,
             isnsRegEntityProtocol,
             isnsRegEntityManagementAddressType,
             isnsRegEntityManagementAddress,
             isnsRegEntityTimestamp,
             isnsRegEntityVersionMin,
             isnsRegEntityVersionMax,
             isnsRegEntityRegistrationPeriod,
             isnsRegEntityInfoNumPortals,
             isnsRegEntityInfoNumPortalGroups,
             isnsRegEntityInfoNumIscsiNodes,
             isnsRegEntityInfoNumFcPorts,
             isnsRegEntityInfoNumFcNodes,
             isnsRegPortalAddressType,
             isnsRegPortalAddress,
             isnsRegPortalPortType,
             isnsRegPortalPort,
             isnsRegPortalSymbolicName,
             isnsRegPortalEsiInterval,
             isnsRegPortalEsiPortType,
             isnsRegPortalEsiPort,
             isnsRegPortalScnPortType,
             isnsRegPortalScnPort,
             isnsRegPortalSecurityInfo,
             isnsRegPgIscsiNodeIndex,
             isnsRegPgIscsiName,
             isnsRegPgPortalPortalIndex,
             isnsRegPgPortalAddressType,
             isnsRegPgPortalAddress,
             isnsRegPgPortalPortType,
             isnsRegPgPortalPort,
             isnsRegPgPGT,
             isnsRegIscsiNodeName,
             isnsRegIscsiNodeType,
             isnsRegIscsiNodeAlias,
             isnsRegIscsiNodeScnTypes,
             isnsRegIscsiNodeWwnToken,
             isnsRegIscsiNodeAuthMethod
                  }
          STATUS                  current
             ::= { isnsGroups 7 }

      isnsServerRegIfcpObjGroup    OBJECT-GROUP
          OBJECTS {





             isnsRegEntityEID,
             isnsRegEntityProtocol,
             isnsRegEntityManagementAddressType,
             isnsRegEntityManagementAddress,
             isnsRegEntityTimestamp,
             isnsRegEntityVersionMin,
             isnsRegEntityVersionMax,
             isnsRegEntityRegistrationPeriod,
             isnsRegEntityInfoNumPortals,
             isnsRegEntityInfoNumPortalGroups,
             isnsRegEntityInfoNumIscsiNodes,
             isnsRegEntityInfoNumFcPorts,
             isnsRegEntityInfoNumFcNodes,
             isnsRegPortalAddressType,
             isnsRegPortalAddress,
             isnsRegPortalPortType,
             isnsRegPortalPort,
             isnsRegPortalSymbolicName,
             isnsRegPortalEsiInterval,
             isnsRegPortalEsiPortType,
             isnsRegPortalEsiPort,
             isnsRegPortalScnPortType,
             isnsRegPortalScnPort,
             isnsRegPortalSecurityInfo,
             isnsRegFcPortID,
             isnsRegFcPortType,
             isnsRegFcPortSymbolicName,
             isnsRegFcPortFabricPortWwn,
             isnsRegFcPortHA,
             isnsRegFcPortAddressType,
             isnsRegFcPortAddress,
             isnsRegFcPortFcCos,
             isnsRegFcPortFc4Types,
             isnsRegFcPortFc4Descr,
             isnsRegFcPortFc4Features,
             isnsRegFcPortScnTypes,
             isnsRegFcPortRole,
             isnsRegFcPortFcNodeWwnn,
             isnsRegFcPortPpnWwn,
             isnsRegFcNodeSymbolicName,
             isnsRegFcNodeAddressType,
             isnsRegFcNodeAddress,
             isnsRegFcNodeIPA,
             isnsRegFcNodeProxyIscsiName,
             isnsRegFcNodeNumFcPorts,
             isnsRegFcNodePortEntityIndex
                  }
          STATUS                  current





             ::= { isnsGroups 8 }

      isnsNotificationsObjGroup    OBJECT-GROUP
          OBJECTS {
             isnsInstanceInfo,
             isnsAddressNotificationType,
             isnsAddressNotification,
             isnsTcpPortNotification,
             isnsUdpPortNotification
                  }
          STATUS                  current
             ::= { isnsGroups 9 }

      isnsServerNotificationGroup  NOTIFICATION-GROUP
          NOTIFICATIONS {
             isnsServerStart,
             isnsServerShutdown
                        }
          STATUS                  current
             ::= { isnsGroups 10 }
   END

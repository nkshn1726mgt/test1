MPLS-LDP-GENERIC-STD-MIB DEFINITIONS ::= BEGIN

   IMPORTS
       OBJECT-TYPE,
       MODULE-IDENTITY,
       Unsigned32
           FROM SNMPv2-SMI                                  -- [RFC2578]

       MODULE-COMPLIANCE,
       OBJECT-GROUP
           FROM SNMPv2-CONF                                 -- [RFC2580]

       RowStatus,
       StorageType
           FROM SNMPv2-TC                                   -- [RFC2579]

       InterfaceIndexOrZero
           FROM IF-MIB                                      -- [RFC2020]

       mplsStdMIB
           FROM MPLS-TC-STD-MIB                             -- [RFC3811]

       mplsLdpEntityLdpId,
       mplsLdpEntityIndex
           FROM MPLS-LDP-STD-MIB                            -- [RFC3813]
       ;

   mplsLdpGenericStdMIB MODULE-IDENTITY
       LAST-UPDATED "200406030000Z"  -- June 6, 2004
       ORGANIZATION "Multiprotocol Label Switching (mpls)
                     Working Group"

       ::= { mplsStdMIB 7 }


   mplsLdpGenericObjects
            OBJECT IDENTIFIER ::= { mplsLdpGenericStdMIB 1 }
   mplsLdpGenericConformance
            OBJECT IDENTIFIER ::= { mplsLdpGenericStdMIB 2 }



   mplsLdpEntityGenericObjects  OBJECT IDENTIFIER ::=
                                 { mplsLdpGenericObjects 1 }







   mplsLdpEntityGenericLRTable OBJECT-TYPE
       SYNTAX SEQUENCE OF MplsLdpEntityGenericLREntry
       MAX-ACCESS not-accessible
       STATUS current
       ::= { mplsLdpEntityGenericObjects 1 }

   mplsLdpEntityGenericLREntry OBJECT-TYPE
       SYNTAX MplsLdpEntityGenericLREntry
       MAX-ACCESS not-accessible
       STATUS current
       INDEX       {  mplsLdpEntityLdpId,
                      mplsLdpEntityIndex,
                      mplsLdpEntityGenericLRMin,
                      mplsLdpEntityGenericLRMax
                   }
       ::= { mplsLdpEntityGenericLRTable 1 }

   MplsLdpEntityGenericLREntry ::= SEQUENCE {
       mplsLdpEntityGenericLRMin           Unsigned32,
       mplsLdpEntityGenericLRMax           Unsigned32,
       mplsLdpEntityGenericLabelSpace      INTEGER,





       mplsLdpEntityGenericIfIndexOrZero   InterfaceIndexOrZero,
       mplsLdpEntityGenericLRStorageType   StorageType,
       mplsLdpEntityGenericLRRowStatus     RowStatus
   }

   mplsLdpEntityGenericLRMin OBJECT-TYPE
       SYNTAX     Unsigned32(0..1048575)
       MAX-ACCESS not-accessible
       STATUS     current
       ::= { mplsLdpEntityGenericLREntry 1 }

   mplsLdpEntityGenericLRMax OBJECT-TYPE
       SYNTAX     Unsigned32(0..1048575)
       MAX-ACCESS not-accessible
       STATUS     current
       ::= { mplsLdpEntityGenericLREntry 2 }

   mplsLdpEntityGenericLabelSpace  OBJECT-TYPE
       SYNTAX      INTEGER {
                             perPlatform(1),
                             perInterface(2)
                            }
       MAX-ACCESS  read-create
       STATUS      current
       DEFVAL { perPlatform }
       ::= { mplsLdpEntityGenericLREntry 3 }

   mplsLdpEntityGenericIfIndexOrZero OBJECT-TYPE
       SYNTAX      InterfaceIndexOrZero
       MAX-ACCESS  read-create
       STATUS      current
       ::= { mplsLdpEntityGenericLREntry 4 }

   mplsLdpEntityGenericLRStorageType  OBJECT-TYPE
       SYNTAX      StorageType
       MAX-ACCESS  read-create
       STATUS      current
       DEFVAL { nonVolatile }
       ::= { mplsLdpEntityGenericLREntry 5 }

   mplsLdpEntityGenericLRRowStatus OBJECT-TYPE
       SYNTAX RowStatus
       MAX-ACCESS read-create
       STATUS current





       ::= { mplsLdpEntityGenericLREntry 6 }


   mplsLdpGenericGroups
       OBJECT IDENTIFIER ::= { mplsLdpGenericConformance 1 }

   mplsLdpGenericCompliances
       OBJECT IDENTIFIER ::= { mplsLdpGenericConformance 2 }


   mplsLdpGenericModuleFullCompliance MODULE-COMPLIANCE
       STATUS current
       MODULE -- this module
           MANDATORY-GROUPS    {
                                  mplsLdpGenericGroup
                               }

       OBJECT       mplsLdpEntityGenericLRRowStatus
       SYNTAX       RowStatus { active(1) }
       WRITE-SYNTAX RowStatus { createAndGo(4), destroy(6) }

       ::= { mplsLdpGenericCompliances 1 }


   mplsLdpGenericModuleReadOnlyCompliance MODULE-COMPLIANCE
       STATUS current
       MODULE -- this module
           MANDATORY-GROUPS    {





                                  mplsLdpGenericGroup
                               }

       OBJECT       mplsLdpEntityGenericLabelSpace
       MIN-ACCESS   read-only

       OBJECT       mplsLdpEntityGenericIfIndexOrZero
       MIN-ACCESS   read-only

       OBJECT       mplsLdpEntityGenericLRStorageType
       MIN-ACCESS   read-only

       OBJECT       mplsLdpEntityGenericLRRowStatus
       SYNTAX       RowStatus { active(1) }
       MIN-ACCESS   read-only

       ::= { mplsLdpGenericCompliances 2 }


   mplsLdpGenericGroup OBJECT-GROUP
       OBJECTS {
       mplsLdpEntityGenericLabelSpace,
       mplsLdpEntityGenericIfIndexOrZero,
       mplsLdpEntityGenericLRStorageType,
       mplsLdpEntityGenericLRRowStatus
       }
       STATUS    current
       ::= { mplsLdpGenericGroups 1 }

   END

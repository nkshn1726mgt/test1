IANATn3270eTC-MIB DEFINITIONS ::= BEGIN

 IMPORTS
      MODULE-IDENTITY, mib-2
          FROM SNMPv2-SMI
      TEXTUAL-CONVENTION
          FROM SNMPv2-TC;

    ianaTn3270eTcMib MODULE-IDENTITY
        LAST-UPDATED "201405220000Z" -- May 22, 2014
        ORGANIZATION "IANA"





        ::= { mib-2 61 }



  IANATn3270eAddrType ::= TEXTUAL-CONVENTION
      STATUS current
      SYNTAX INTEGER {
                      unknown(0),
                      ipv4(1),
                      ipv6(2)
                     }

  IANATn3270eAddress ::= TEXTUAL-CONVENTION
      STATUS current
      SYNTAX OCTET STRING (SIZE (0..255))

  IANATn3270eClientType ::= TEXTUAL-CONVENTION
      STATUS current
      SYNTAX INTEGER {
                      none(1),
                      other(2),
                      ipv4(3),
                      ipv6(4),
                      domainName(5),
                      truncDomainName(6),
                      string(7),
                      certificate(8),
                      userId(9),
                      x509dn(10)
                     }

  IANATn3270Functions ::= TEXTUAL-CONVENTION
      STATUS current
      SYNTAX BITS {
                   transmitBinary(0),-- rfc856
                   timemark(1),      -- rfc860
                   endOfRecord(2),   -- rfc885
                   terminalType(3),  -- rfc1091
                   tn3270Regime(4),  -- rfc1041
                   scsCtlCodes(5),   -- rfc2355
                   dataStreamCtl(6), -- rfc2355
                   responses(7),     -- rfc2355
                   bindImage(8),     -- rfc2355
                   sysreq(9)         -- rfc2355
                  }

  IANATn3270ResourceType ::= TEXTUAL-CONVENTION
      STATUS current
      SYNTAX INTEGER {
                      other(1),
                      terminal(2),
                      printer(3),
                      terminalOrPrinter(4)
                     }

  IANATn3270DeviceType ::= TEXTUAL-CONVENTION
      STATUS current
      SYNTAX INTEGER {
                      ibm3278d2(1),    -- (24 row x 80 col display)
                      ibm3278d2E(2),   -- (24 row x 80 col display)
                      ibm3278d3(3),    -- (32 row x 80 col display)
                      ibm3278d3E(4),   -- (32 row x 80 col display)
                      ibm3278d4(5),    -- (43 row x 80 col display)
                      ibm3278d4E(6),   -- (43 row x 80 col display)
                      ibm3278d5(7),    -- (27 row x 132 col display)
                      ibm3278d5E(8),   -- (27 row x 132 col display)
                      ibmDynamic(9),   -- (no pre-defined display size)

                      ibm3287d1(10),

                      unknown(100)
                     }

  IANATn3270eLogData ::= TEXTUAL-CONVENTION
      STATUS current
      SYNTAX OCTET STRING (SIZE (0 | 6..2048))

  END

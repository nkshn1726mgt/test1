MPLS-L3VPN-STD-MIB DEFINITIONS ::= BEGIN
IMPORTS
   MODULE-IDENTITY, OBJECT-TYPE, NOTIFICATION-TYPE,
   Integer32, Counter32, Unsigned32, Gauge32
      FROM SNMPv2-SMI                                     -- [RFC2578]
   MODULE-COMPLIANCE, OBJECT-GROUP, NOTIFICATION-GROUP
      FROM SNMPv2-CONF                                    -- [RFC2580]
   TEXTUAL-CONVENTION, TruthValue, RowStatus,
   TimeStamp, StorageType
      FROM SNMPv2-TC                                      -- [RFC2579]
   InterfaceIndex, InterfaceIndexOrZero
      FROM IF-MIB                                         -- [RFC2863]
   VPNIdOrZero
     FROM VPN-TC-STD-MIB                                  -- [RFC4265]
   SnmpAdminString
      FROM SNMP-FRAMEWORK-MIB                             -- [RFC3411]
   IANAipRouteProtocol
      FROM IANA-RTPROTO-MIB                               -- [RTPROTO]
   InetAddress, InetAddressType,
   InetAddressPrefixLength,
   InetAutonomousSystemNumber
      FROM INET-ADDRESS-MIB                               -- [RFC4001]
   mplsStdMIB
      FROM MPLS-TC-STD-MIB                                -- [RFC3811]





   MplsIndexType
      FROM MPLS-LSR-STD-MIB                               -- [RFC3813]
   ;

mplsL3VpnMIB MODULE-IDENTITY
   LAST-UPDATED "200601230000Z"  -- 23 January 2006
   ORGANIZATION "IETF Layer-3 Virtual Private
                 Networks Working Group."
   ::= { mplsStdMIB 11 }

MplsL3VpnName ::= TEXTUAL-CONVENTION
   STATUS        current
   SYNTAX OCTET STRING (SIZE (0..31))

MplsL3VpnRouteDistinguisher ::= TEXTUAL-CONVENTION
   STATUS        current
   SYNTAX  OCTET STRING(SIZE (0..256))

MplsL3VpnRtType ::= TEXTUAL-CONVENTION
   STATUS        current
   SYNTAX INTEGER { import(1), export(2), both(3) }

mplsL3VpnNotifications OBJECT IDENTIFIER ::= { mplsL3VpnMIB 0 }
mplsL3VpnObjects       OBJECT IDENTIFIER ::= { mplsL3VpnMIB 1 }
mplsL3VpnScalars       OBJECT IDENTIFIER ::= { mplsL3VpnObjects 1 }
mplsL3VpnConf          OBJECT IDENTIFIER ::= { mplsL3VpnObjects 2 }
mplsL3VpnPerf          OBJECT IDENTIFIER ::= { mplsL3VpnObjects 3 }
mplsL3VpnRoute         OBJECT IDENTIFIER ::= { mplsL3VpnObjects 4 }
mplsL3VpnConformance   OBJECT IDENTIFIER ::= { mplsL3VpnMIB 2 }


mplsL3VpnConfiguredVrfs OBJECT-TYPE
   SYNTAX        Unsigned32
   MAX-ACCESS    read-only
   STATUS        current
   ::= { mplsL3VpnScalars 1 }

mplsL3VpnActiveVrfs OBJECT-TYPE
   SYNTAX        Gauge32
   MAX-ACCESS    read-only
   STATUS        current





   ::= { mplsL3VpnScalars 2 }

mplsL3VpnConnectedInterfaces OBJECT-TYPE
   SYNTAX        Gauge32
   MAX-ACCESS    read-only
   STATUS        current
   ::= { mplsL3VpnScalars 3 }

mplsL3VpnNotificationEnable OBJECT-TYPE
   SYNTAX        TruthValue
   MAX-ACCESS    read-write
   STATUS        current
   DEFVAL { false }
   ::= { mplsL3VpnScalars 4 }

mplsL3VpnVrfConfMaxPossRts  OBJECT-TYPE
   SYNTAX        Unsigned32
   MAX-ACCESS    read-only
   STATUS        current
   ::= { mplsL3VpnScalars 5 }

mplsL3VpnVrfConfRteMxThrshTime  OBJECT-TYPE
   SYNTAX        Unsigned32
   UNITS         "seconds"
   MAX-ACCESS    read-only
   STATUS        current





   DEFVAL { 0 }
   ::= { mplsL3VpnScalars 6 }

mplsL3VpnIllLblRcvThrsh OBJECT-TYPE
   SYNTAX        Unsigned32
   MAX-ACCESS    read-write
   STATUS        current
   ::= { mplsL3VpnScalars 7 }


mplsL3VpnIfConfTable  OBJECT-TYPE
   SYNTAX        SEQUENCE OF MplsL3VpnIfConfEntry
   MAX-ACCESS    not-accessible
   STATUS        current
   ::= { mplsL3VpnConf 1 }

mplsL3VpnIfConfEntry OBJECT-TYPE
   SYNTAX        MplsL3VpnIfConfEntry
   MAX-ACCESS    not-accessible
   STATUS        current





   INDEX       { mplsL3VpnVrfName, mplsL3VpnIfConfIndex }
   ::= { mplsL3VpnIfConfTable 1 }

MplsL3VpnIfConfEntry ::= SEQUENCE {
  mplsL3VpnIfConfIndex             InterfaceIndex,
  mplsL3VpnIfVpnClassification     INTEGER,
  mplsL3VpnIfVpnRouteDistProtocol  BITS,
  mplsL3VpnIfConfStorageType       StorageType,
  mplsL3VpnIfConfRowStatus         RowStatus
}

mplsL3VpnIfConfIndex OBJECT-TYPE
   SYNTAX        InterfaceIndex
   MAX-ACCESS    not-accessible
   STATUS        current
   ::= { mplsL3VpnIfConfEntry 1 }

mplsL3VpnIfVpnClassification OBJECT-TYPE
   SYNTAX        INTEGER { carrierOfCarrier (1),
                           enterprise (2),
                           interProvider (3)
   }
   MAX-ACCESS    read-create
   STATUS        current
   DEFVAL { enterprise }
   ::= { mplsL3VpnIfConfEntry 2 }

mplsL3VpnIfVpnRouteDistProtocol OBJECT-TYPE
   SYNTAX        BITS { none (0),
                        bgp (1),
                        ospf (2),
                        rip(3),
                        isis(4),





                        static(5),
                        other (6)
   }
   MAX-ACCESS    read-create
   STATUS        current
   ::= { mplsL3VpnIfConfEntry 3 }

mplsL3VpnIfConfStorageType  OBJECT-TYPE
   SYNTAX      StorageType
   MAX-ACCESS  read-create
   STATUS      current
   DEFVAL { volatile }
   ::= { mplsL3VpnIfConfEntry 4 }

mplsL3VpnIfConfRowStatus  OBJECT-TYPE
   SYNTAX      RowStatus
   MAX-ACCESS  read-create
   STATUS      current
   ::= { mplsL3VpnIfConfEntry 5 }






mplsL3VpnVrfTable  OBJECT-TYPE
   SYNTAX        SEQUENCE OF MplsL3VpnVrfEntry
   MAX-ACCESS    not-accessible
   STATUS        current
   ::= { mplsL3VpnConf 2 }

mplsL3VpnVrfEntry OBJECT-TYPE
   SYNTAX        MplsL3VpnVrfEntry
   MAX-ACCESS    not-accessible
   STATUS        current
   INDEX       { mplsL3VpnVrfName }
   ::= { mplsL3VpnVrfTable 1 }
MplsL3VpnVrfEntry ::= SEQUENCE {
  mplsL3VpnVrfName                      MplsL3VpnName,
  mplsL3VpnVrfVpnId                     VPNIdOrZero,
  mplsL3VpnVrfDescription               SnmpAdminString,
  mplsL3VpnVrfRD                        MplsL3VpnRouteDistinguisher,
  mplsL3VpnVrfCreationTime              TimeStamp,
  mplsL3VpnVrfOperStatus                INTEGER,
  mplsL3VpnVrfActiveInterfaces          Gauge32,
  mplsL3VpnVrfAssociatedInterfaces      Unsigned32,
  mplsL3VpnVrfConfMidRteThresh          Unsigned32,
  mplsL3VpnVrfConfHighRteThresh         Unsigned32,
  mplsL3VpnVrfConfMaxRoutes             Unsigned32,
  mplsL3VpnVrfConfLastChanged           TimeStamp,
  mplsL3VpnVrfConfRowStatus             RowStatus,
  mplsL3VpnVrfConfAdminStatus           INTEGER,
  mplsL3VpnVrfConfStorageType           StorageType
}

mplsL3VpnVrfName OBJECT-TYPE
   SYNTAX        MplsL3VpnName
   MAX-ACCESS    not-accessible
   STATUS        current
   ::= { mplsL3VpnVrfEntry 1 }

mplsL3VpnVrfVpnId OBJECT-TYPE
   SYNTAX        VPNIdOrZero
   MAX-ACCESS    read-create
   STATUS        current
   ::= { mplsL3VpnVrfEntry 2 }

mplsL3VpnVrfDescription OBJECT-TYPE
   SYNTAX        SnmpAdminString
   MAX-ACCESS    read-create
   STATUS        current
   DEFVAL { "" }
   ::= { mplsL3VpnVrfEntry 3 }

mplsL3VpnVrfRD OBJECT-TYPE
   SYNTAX        MplsL3VpnRouteDistinguisher
   MAX-ACCESS    read-create
   STATUS        current
   DEFVAL { "" }
   ::= { mplsL3VpnVrfEntry 4 }

mplsL3VpnVrfCreationTime OBJECT-TYPE
   SYNTAX        TimeStamp
   MAX-ACCESS    read-only
   STATUS        current
   ::= { mplsL3VpnVrfEntry 5 }





mplsL3VpnVrfOperStatus OBJECT-TYPE
   SYNTAX        INTEGER { up (1),
                           down (2)
                         }
   MAX-ACCESS    read-only
   STATUS        current
   ::= { mplsL3VpnVrfEntry 6 }

mplsL3VpnVrfActiveInterfaces OBJECT-TYPE
   SYNTAX        Gauge32
   MAX-ACCESS    read-only
   STATUS        current
   ::= { mplsL3VpnVrfEntry 7 }

mplsL3VpnVrfAssociatedInterfaces OBJECT-TYPE
   SYNTAX        Unsigned32
   MAX-ACCESS    read-only
   STATUS        current
   ::= { mplsL3VpnVrfEntry 8 }

mplsL3VpnVrfConfMidRteThresh    OBJECT-TYPE
   SYNTAX        Unsigned32
   MAX-ACCESS    read-create





   STATUS        current
  DEFVAL { 0 }
  ::= { mplsL3VpnVrfEntry 9 }

mplsL3VpnVrfConfHighRteThresh  OBJECT-TYPE
   SYNTAX        Unsigned32
   MAX-ACCESS    read-create
   STATUS        current
   DEFVAL { 0 }
  ::= { mplsL3VpnVrfEntry 10 }

mplsL3VpnVrfConfMaxRoutes  OBJECT-TYPE
   SYNTAX        Unsigned32
   MAX-ACCESS    read-create
   STATUS        current
   DEFVAL { 0 }
  ::= { mplsL3VpnVrfEntry 11 }

mplsL3VpnVrfConfLastChanged  OBJECT-TYPE
   SYNTAX        TimeStamp
   MAX-ACCESS    read-only
   STATUS        current
  ::= { mplsL3VpnVrfEntry 12 }

mplsL3VpnVrfConfRowStatus OBJECT-TYPE
   SYNTAX        RowStatus
   MAX-ACCESS    read-create
   STATUS        current
  ::= { mplsL3VpnVrfEntry 13 }

mplsL3VpnVrfConfAdminStatus OBJECT-TYPE
   SYNTAX     INTEGER {
                      up(1),     -- ready to pass packets
                      down(2),   -- can't pass packets
                      testing(3) -- in some test mode
                }
   MAX-ACCESS    read-create
   STATUS        current
  ::= { mplsL3VpnVrfEntry 14 }

mplsL3VpnVrfConfStorageType  OBJECT-TYPE
   SYNTAX      StorageType
   MAX-ACCESS  read-create
   STATUS      current
   DEFVAL { volatile }
   ::= { mplsL3VpnVrfEntry 15 }


mplsL3VpnVrfRTTable OBJECT-TYPE
    SYNTAX        SEQUENCE OF MplsL3VpnVrfRTEntry
    MAX-ACCESS    not-accessible
    STATUS        current
    ::= { mplsL3VpnConf 3 }

mplsL3VpnVrfRTEntry OBJECT-TYPE
    SYNTAX        MplsL3VpnVrfRTEntry
    MAX-ACCESS    not-accessible





    STATUS        current
    INDEX  { mplsL3VpnVrfName, mplsL3VpnVrfRTIndex,
             mplsL3VpnVrfRTType }
    ::= { mplsL3VpnVrfRTTable 1 }

MplsL3VpnVrfRTEntry ::= SEQUENCE {
     mplsL3VpnVrfRTIndex       Unsigned32,
     mplsL3VpnVrfRTType        MplsL3VpnRtType,
     mplsL3VpnVrfRT            MplsL3VpnRouteDistinguisher,
     mplsL3VpnVrfRTDescr       SnmpAdminString,
     mplsL3VpnVrfRTRowStatus   RowStatus,
     mplsL3VpnVrfRTStorageType StorageType
   }

mplsL3VpnVrfRTIndex OBJECT-TYPE
   SYNTAX        Unsigned32 (1..4294967295)
   MAX-ACCESS    not-accessible
   STATUS        current
   ::= { mplsL3VpnVrfRTEntry 2 }

mplsL3VpnVrfRTType OBJECT-TYPE
   SYNTAX        MplsL3VpnRtType
   MAX-ACCESS    not-accessible
   STATUS        current
   ::= { mplsL3VpnVrfRTEntry 3 }

mplsL3VpnVrfRT OBJECT-TYPE
   SYNTAX        MplsL3VpnRouteDistinguisher
   MAX-ACCESS    read-create
   STATUS        current
   DEFVAL { "" }
   ::= { mplsL3VpnVrfRTEntry 4 }

mplsL3VpnVrfRTDescr OBJECT-TYPE
   SYNTAX        SnmpAdminString





   MAX-ACCESS    read-create
   STATUS        current
   DEFVAL { "" }
   ::= { mplsL3VpnVrfRTEntry 5 }

mplsL3VpnVrfRTRowStatus OBJECT-TYPE
   SYNTAX        RowStatus
   MAX-ACCESS    read-create
   STATUS        current
   ::= { mplsL3VpnVrfRTEntry 6 }

mplsL3VpnVrfRTStorageType OBJECT-TYPE
   SYNTAX        StorageType
   MAX-ACCESS    read-create
   STATUS        current
   DEFVAL { volatile }
   ::= { mplsL3VpnVrfRTEntry 7 }


mplsL3VpnVrfSecTable  OBJECT-TYPE
   SYNTAX        SEQUENCE OF MplsL3VpnVrfSecEntry
   MAX-ACCESS    not-accessible
   STATUS        current
   ::= { mplsL3VpnConf 6 }

mplsL3VpnVrfSecEntry OBJECT-TYPE
   SYNTAX        MplsL3VpnVrfSecEntry
   MAX-ACCESS    not-accessible
   STATUS        current
   AUGMENTS      { mplsL3VpnVrfEntry }
      ::= { mplsL3VpnVrfSecTable 1 }

MplsL3VpnVrfSecEntry ::= SEQUENCE {
       mplsL3VpnVrfSecIllegalLblVltns     Counter32,
       mplsL3VpnVrfSecDiscontinuityTime   TimeStamp
}

mplsL3VpnVrfSecIllegalLblVltns OBJECT-TYPE
   SYNTAX        Counter32
   MAX-ACCESS    read-only
   STATUS        current
   ::= { mplsL3VpnVrfSecEntry 1 }

mplsL3VpnVrfSecDiscontinuityTime  OBJECT-TYPE
   SYNTAX              TimeStamp
   MAX-ACCESS          read-only
   STATUS              current
   ::= { mplsL3VpnVrfSecEntry 2 }



mplsL3VpnVrfPerfTable  OBJECT-TYPE
   SYNTAX        SEQUENCE OF MplsL3VpnVrfPerfEntry
   MAX-ACCESS    not-accessible
   STATUS        current
   ::= { mplsL3VpnPerf 1 }

mplsL3VpnVrfPerfEntry OBJECT-TYPE
   SYNTAX        MplsL3VpnVrfPerfEntry
   MAX-ACCESS    not-accessible
   STATUS        current
   AUGMENTS      { mplsL3VpnVrfEntry }
      ::= { mplsL3VpnVrfPerfTable 1 }

MplsL3VpnVrfPerfEntry ::= SEQUENCE {
   mplsL3VpnVrfPerfRoutesAdded       Counter32,
   mplsL3VpnVrfPerfRoutesDeleted     Counter32,
   mplsL3VpnVrfPerfCurrNumRoutes     Gauge32,
   mplsL3VpnVrfPerfRoutesDropped     Counter32,
   mplsL3VpnVrfPerfDiscTime          TimeStamp
}

mplsL3VpnVrfPerfRoutesAdded OBJECT-TYPE
   SYNTAX        Counter32
   MAX-ACCESS    read-only
   STATUS        current
   ::= { mplsL3VpnVrfPerfEntry 1 }

mplsL3VpnVrfPerfRoutesDeleted OBJECT-TYPE
   SYNTAX        Counter32
   MAX-ACCESS    read-only
   STATUS        current
   ::= { mplsL3VpnVrfPerfEntry 2 }

mplsL3VpnVrfPerfCurrNumRoutes     OBJECT-TYPE





   SYNTAX        Gauge32
   MAX-ACCESS    read-only
   STATUS        current
   ::= { mplsL3VpnVrfPerfEntry 3 }


mplsL3VpnVrfPerfRoutesDropped OBJECT-TYPE
   SYNTAX        Counter32
   MAX-ACCESS    read-only
   STATUS        current
  ::= { mplsL3VpnVrfPerfEntry 4 }

mplsL3VpnVrfPerfDiscTime  OBJECT-TYPE
   SYNTAX              TimeStamp
   MAX-ACCESS          read-only
   STATUS              current
  ::= { mplsL3VpnVrfPerfEntry 5 }


mplsL3VpnVrfRteTable  OBJECT-TYPE
   SYNTAX        SEQUENCE OF MplsL3VpnVrfRteEntry
   MAX-ACCESS    not-accessible
   STATUS        current
   ::= { mplsL3VpnRoute 1 }

mplsL3VpnVrfRteEntry OBJECT-TYPE
   SYNTAX        MplsL3VpnVrfRteEntry
   MAX-ACCESS    not-accessible
   STATUS        current

      INDEX  { mplsL3VpnVrfName,
               mplsL3VpnVrfRteInetCidrDestType,
               mplsL3VpnVrfRteInetCidrDest,
               mplsL3VpnVrfRteInetCidrPfxLen,
               mplsL3VpnVrfRteInetCidrPolicy,
               mplsL3VpnVrfRteInetCidrNHopType,
               mplsL3VpnVrfRteInetCidrNextHop
      }
      ::= { mplsL3VpnVrfRteTable 1 }

MplsL3VpnVrfRteEntry ::= SEQUENCE {
         mplsL3VpnVrfRteInetCidrDestType     InetAddressType,
         mplsL3VpnVrfRteInetCidrDest         InetAddress,
         mplsL3VpnVrfRteInetCidrPfxLen       InetAddressPrefixLength,
         mplsL3VpnVrfRteInetCidrPolicy       OBJECT IDENTIFIER,
         mplsL3VpnVrfRteInetCidrNHopType     InetAddressType,
         mplsL3VpnVrfRteInetCidrNextHop      InetAddress,
         mplsL3VpnVrfRteInetCidrIfIndex      InterfaceIndexOrZero,
         mplsL3VpnVrfRteInetCidrType         INTEGER,
         mplsL3VpnVrfRteInetCidrProto        IANAipRouteProtocol,
         mplsL3VpnVrfRteInetCidrAge          Gauge32,
         mplsL3VpnVrfRteInetCidrNextHopAS    InetAutonomousSystemNumber,
         mplsL3VpnVrfRteInetCidrMetric1      Integer32,
         mplsL3VpnVrfRteInetCidrMetric2      Integer32,





         mplsL3VpnVrfRteInetCidrMetric3      Integer32,
         mplsL3VpnVrfRteInetCidrMetric4      Integer32,
         mplsL3VpnVrfRteInetCidrMetric5      Integer32,
         mplsL3VpnVrfRteXCPointer            MplsIndexType,
         mplsL3VpnVrfRteInetCidrStatus       RowStatus
       }

    mplsL3VpnVrfRteInetCidrDestType OBJECT-TYPE
        SYNTAX     InetAddressType
        MAX-ACCESS not-accessible
        STATUS     current
        ::= { mplsL3VpnVrfRteEntry 1 }

    mplsL3VpnVrfRteInetCidrDest OBJECT-TYPE
        SYNTAX     InetAddress
        MAX-ACCESS not-accessible
        STATUS     current
        ::= { mplsL3VpnVrfRteEntry 2 }

    mplsL3VpnVrfRteInetCidrPfxLen OBJECT-TYPE
        SYNTAX     InetAddressPrefixLength (0..128)
        MAX-ACCESS not-accessible
        STATUS     current
        ::= { mplsL3VpnVrfRteEntry 3 }

    mplsL3VpnVrfRteInetCidrPolicy OBJECT-TYPE
        SYNTAX     OBJECT IDENTIFIER
        MAX-ACCESS not-accessible
        STATUS     current
        ::= { mplsL3VpnVrfRteEntry 4 }

    mplsL3VpnVrfRteInetCidrNHopType OBJECT-TYPE
        SYNTAX     InetAddressType
        MAX-ACCESS not-accessible
        STATUS     current
        ::= { mplsL3VpnVrfRteEntry 5 }

    mplsL3VpnVrfRteInetCidrNextHop OBJECT-TYPE
        SYNTAX     InetAddress
        MAX-ACCESS not-accessible
        STATUS     current





        ::= { mplsL3VpnVrfRteEntry 6 }

    mplsL3VpnVrfRteInetCidrIfIndex OBJECT-TYPE
        SYNTAX     InterfaceIndexOrZero
        MAX-ACCESS read-create
        STATUS     current
        DEFVAL { 0 }
        ::= { mplsL3VpnVrfRteEntry 7 }

    mplsL3VpnVrfRteInetCidrType OBJECT-TYPE
        SYNTAX     INTEGER {
                    other    (1), -- not specified by this MIB
                    reject   (2), -- route which discards traffic and
                    local    (3), -- local interface
                    remote   (4), -- remote destination
                    blackhole(5)  -- route which discards traffic
                 }
        MAX-ACCESS read-create
        STATUS     current
        DEFVAL { other }
        ::= { mplsL3VpnVrfRteEntry 8 }

    mplsL3VpnVrfRteInetCidrProto OBJECT-TYPE
        SYNTAX     IANAipRouteProtocol
        MAX-ACCESS read-only
        STATUS     current
        ::= { mplsL3VpnVrfRteEntry 9 }

    mplsL3VpnVrfRteInetCidrAge OBJECT-TYPE
        SYNTAX     Gauge32
        MAX-ACCESS read-only
        STATUS     current
        ::= { mplsL3VpnVrfRteEntry 10 }

    mplsL3VpnVrfRteInetCidrNextHopAS OBJECT-TYPE
        SYNTAX     InetAutonomousSystemNumber
        MAX-ACCESS read-create
        STATUS     current
        DEFVAL { 0 }
        ::= { mplsL3VpnVrfRteEntry 11 }

    mplsL3VpnVrfRteInetCidrMetric1 OBJECT-TYPE
        SYNTAX     Integer32 (-1 | 0..2147483647)
        MAX-ACCESS read-create
        STATUS     current
        DEFVAL { -1 }
        ::= { mplsL3VpnVrfRteEntry 12 }

    mplsL3VpnVrfRteInetCidrMetric2 OBJECT-TYPE
        SYNTAX     Integer32 (-1 | 0..2147483647)
        MAX-ACCESS read-create
        STATUS     current
        DEFVAL { -1 }
        ::= { mplsL3VpnVrfRteEntry 13 }

    mplsL3VpnVrfRteInetCidrMetric3 OBJECT-TYPE
        SYNTAX     Integer32 (-1 | 0..2147483647)
        MAX-ACCESS read-create
        STATUS     current
        DEFVAL { -1 }
        ::= { mplsL3VpnVrfRteEntry 14 }

    mplsL3VpnVrfRteInetCidrMetric4 OBJECT-TYPE
        SYNTAX     Integer32 (-1 | 0..2147483647)
        MAX-ACCESS read-create
        STATUS     current
        DEFVAL { -1 }
        ::= { mplsL3VpnVrfRteEntry 15 }






    mplsL3VpnVrfRteInetCidrMetric5 OBJECT-TYPE
        SYNTAX     Integer32 (-1 | 0..2147483647)
        MAX-ACCESS read-create
        STATUS     current
        DEFVAL { -1 }
        ::= { mplsL3VpnVrfRteEntry 16 }

   mplsL3VpnVrfRteXCPointer  OBJECT-TYPE
      SYNTAX        MplsIndexType
      MAX-ACCESS    read-create
      STATUS        current
       ::= { mplsL3VpnVrfRteEntry 17 }

    mplsL3VpnVrfRteInetCidrStatus OBJECT-TYPE
        SYNTAX     RowStatus
        MAX-ACCESS read-create
        STATUS     current
        ::= { mplsL3VpnVrfRteEntry 18 }


mplsL3VpnVrfUp NOTIFICATION-TYPE
   OBJECTS     { mplsL3VpnIfConfRowStatus,
                 mplsL3VpnVrfOperStatus
               }
   STATUS      current
   ::= { mplsL3VpnNotifications 1 }

mplsL3VpnVrfDown NOTIFICATION-TYPE
   OBJECTS     { mplsL3VpnIfConfRowStatus,
                 mplsL3VpnVrfOperStatus
               }
   STATUS      current
   ::= { mplsL3VpnNotifications 2 }

mplsL3VpnVrfRouteMidThreshExceeded NOTIFICATION-TYPE
   OBJECTS     { mplsL3VpnVrfPerfCurrNumRoutes,
                 mplsL3VpnVrfConfMidRteThresh





               }
   STATUS      current
   ::= { mplsL3VpnNotifications 3 }

mplsL3VpnVrfNumVrfRouteMaxThreshExceeded NOTIFICATION-TYPE
   OBJECTS     { mplsL3VpnVrfPerfCurrNumRoutes,
                 mplsL3VpnVrfConfHighRteThresh
               }
   STATUS      current
   ::= { mplsL3VpnNotifications 4 }

mplsL3VpnNumVrfSecIllglLblThrshExcd NOTIFICATION-TYPE
   OBJECTS     { mplsL3VpnVrfSecIllegalLblVltns }
   STATUS      current
   ::= { mplsL3VpnNotifications 5 }


mplsL3VpnNumVrfRouteMaxThreshCleared NOTIFICATION-TYPE
   OBJECTS     { mplsL3VpnVrfPerfCurrNumRoutes,
                 mplsL3VpnVrfConfHighRteThresh
               }
   STATUS      current
   ::= { mplsL3VpnNotifications 6 }

mplsL3VpnGroups
      OBJECT IDENTIFIER ::= { mplsL3VpnConformance 1 }

mplsL3VpnCompliances





      OBJECT IDENTIFIER ::= { mplsL3VpnConformance 2 }


mplsL3VpnModuleFullCompliance MODULE-COMPLIANCE
      STATUS current
      MODULE -- this module
         MANDATORY-GROUPS    { mplsL3VpnScalarGroup,
                               mplsL3VpnVrfGroup,
                               mplsL3VpnIfGroup,
                               mplsL3VpnPerfGroup,
                               mplsL3VpnVrfRteGroup,
                               mplsL3VpnVrfRTGroup,
                               mplsL3VpnSecGroup,
                               mplsL3VpnNotificationGroup
                             }

   GROUP       mplsL3VpnPerfRouteGroup

   OBJECT       mplsL3VpnIfConfRowStatus
   SYNTAX       RowStatus { active(1), notInService(2) }
   WRITE-SYNTAX RowStatus { active(1), notInService(2),
                            createAndGo(4), destroy(6)
                          }


   OBJECT       mplsL3VpnVrfConfRowStatus
   SYNTAX       RowStatus { active(1), notInService(2) }
   WRITE-SYNTAX RowStatus { active(1), notInService(2),
                            createAndGo(4), destroy(6)
                          }
   OBJECT       mplsL3VpnVrfRTRowStatus
   SYNTAX       RowStatus { active(1), notInService(2) }
   WRITE-SYNTAX RowStatus { active(1), notInService(2),
                            createAndGo(4), destroy(6)
                          }





   ::= { mplsL3VpnCompliances 1 }



mplsL3VpnModuleReadOnlyCompliance MODULE-COMPLIANCE
      STATUS current

      MODULE -- this module
         MANDATORY-GROUPS    { mplsL3VpnScalarGroup,
                               mplsL3VpnVrfGroup,
                               mplsL3VpnIfGroup,
                               mplsL3VpnPerfGroup,
                               mplsL3VpnVrfRteGroup,
                               mplsL3VpnVrfRTGroup,
                               mplsL3VpnSecGroup,
                               mplsL3VpnNotificationGroup
                             }

   GROUP       mplsL3VpnPerfRouteGroup

   OBJECT       mplsL3VpnIfConfRowStatus
   SYNTAX       RowStatus { active(1) }
   MIN-ACCESS   read-only

   OBJECT       mplsL3VpnVrfConfRowStatus
   SYNTAX       RowStatus { active(1) }
   MIN-ACCESS   read-only

   OBJECT       mplsL3VpnVrfRTRowStatus
   SYNTAX       RowStatus { active(1) }
   MIN-ACCESS   read-only

   OBJECT       mplsL3VpnIfVpnClassification
   MIN-ACCESS   read-only





   OBJECT       mplsL3VpnIfVpnRouteDistProtocol
   MIN-ACCESS   read-only

   OBJECT       mplsL3VpnIfConfStorageType
   MIN-ACCESS   read-only

   OBJECT       mplsL3VpnVrfVpnId
   MIN-ACCESS   read-only

   OBJECT       mplsL3VpnVrfDescription
   MIN-ACCESS   read-only

   OBJECT       mplsL3VpnVrfRD
   MIN-ACCESS   read-only

   OBJECT       mplsL3VpnVrfConfMidRteThresh
   MIN-ACCESS   read-only

   OBJECT       mplsL3VpnVrfConfHighRteThresh
   MIN-ACCESS   read-only

   OBJECT       mplsL3VpnVrfConfMaxRoutes
   MIN-ACCESS   read-only

   OBJECT       mplsL3VpnVrfConfStorageType
   MIN-ACCESS   read-only

   OBJECT       mplsL3VpnVrfRT
   MIN-ACCESS   read-only

   OBJECT       mplsL3VpnVrfRTDescr
   MIN-ACCESS   read-only

   OBJECT       mplsL3VpnVrfRTStorageType
   MIN-ACCESS   read-only






   OBJECT       mplsL3VpnVrfRteInetCidrIfIndex
   MIN-ACCESS   read-only

   OBJECT       mplsL3VpnVrfRteInetCidrType
   MIN-ACCESS   read-only

   OBJECT       mplsL3VpnVrfRteInetCidrNextHopAS
   MIN-ACCESS   read-only

   OBJECT       mplsL3VpnVrfRteInetCidrMetric1
   MIN-ACCESS   read-only

   OBJECT       mplsL3VpnVrfRteInetCidrMetric2
   MIN-ACCESS   read-only

   OBJECT       mplsL3VpnVrfRteInetCidrMetric3
   MIN-ACCESS   read-only

   OBJECT       mplsL3VpnVrfRteInetCidrMetric4
   MIN-ACCESS   read-only

   OBJECT       mplsL3VpnVrfRteInetCidrMetric5
   MIN-ACCESS   read-only

   OBJECT       mplsL3VpnVrfRteXCPointer
   MIN-ACCESS   read-only

   OBJECT       mplsL3VpnVrfRteInetCidrStatus
   SYNTAX       RowStatus { active(1) }
   MIN-ACCESS   read-only
   ::= { mplsL3VpnCompliances 2 }


   mplsL3VpnScalarGroup OBJECT-GROUP
      OBJECTS { mplsL3VpnConfiguredVrfs,
                mplsL3VpnActiveVrfs,
                mplsL3VpnConnectedInterfaces,





                mplsL3VpnNotificationEnable,
                mplsL3VpnVrfConfMaxPossRts,
                mplsL3VpnVrfConfRteMxThrshTime,
                mplsL3VpnIllLblRcvThrsh
             }
      STATUS  current
      ::= { mplsL3VpnGroups 1 }

   mplsL3VpnVrfGroup OBJECT-GROUP
      OBJECTS { mplsL3VpnVrfVpnId,
                mplsL3VpnVrfDescription,
                mplsL3VpnVrfRD,
                mplsL3VpnVrfCreationTime,
                mplsL3VpnVrfOperStatus,
                mplsL3VpnVrfActiveInterfaces,
                mplsL3VpnVrfAssociatedInterfaces,
                mplsL3VpnVrfConfMidRteThresh,
                mplsL3VpnVrfConfHighRteThresh,
                mplsL3VpnVrfConfMaxRoutes,
                mplsL3VpnVrfConfLastChanged,
                mplsL3VpnVrfConfRowStatus,
                mplsL3VpnVrfConfAdminStatus,
                mplsL3VpnVrfConfStorageType
       }
      STATUS  current
      ::= { mplsL3VpnGroups 2 }

   mplsL3VpnIfGroup OBJECT-GROUP
        OBJECTS { mplsL3VpnIfVpnClassification,
                  mplsL3VpnIfVpnRouteDistProtocol,
                  mplsL3VpnIfConfStorageType,
                  mplsL3VpnIfConfRowStatus
           }
      STATUS  current
      ::= { mplsL3VpnGroups 3 }

   mplsL3VpnPerfGroup OBJECT-GROUP
      OBJECTS { mplsL3VpnVrfPerfRoutesAdded,
                mplsL3VpnVrfPerfRoutesDeleted,





                mplsL3VpnVrfPerfCurrNumRoutes
             }
      STATUS  current
      ::= { mplsL3VpnGroups 4 }

   mplsL3VpnPerfRouteGroup OBJECT-GROUP
      OBJECTS { mplsL3VpnVrfPerfRoutesDropped,
                mplsL3VpnVrfPerfDiscTime
             }
      STATUS  current
      ::= { mplsL3VpnGroups 5 }

   mplsL3VpnSecGroup OBJECT-GROUP
      OBJECTS { mplsL3VpnVrfSecIllegalLblVltns,
                mplsL3VpnVrfSecDiscontinuityTime }
      STATUS  current
      ::= { mplsL3VpnGroups 7 }

   mplsL3VpnVrfRteGroup OBJECT-GROUP
      OBJECTS {
            mplsL3VpnVrfRteInetCidrIfIndex,
            mplsL3VpnVrfRteInetCidrType,
            mplsL3VpnVrfRteInetCidrProto,
            mplsL3VpnVrfRteInetCidrAge,
            mplsL3VpnVrfRteInetCidrNextHopAS,
            mplsL3VpnVrfRteInetCidrMetric1,
            mplsL3VpnVrfRteInetCidrMetric2,
            mplsL3VpnVrfRteInetCidrMetric3,
            mplsL3VpnVrfRteInetCidrMetric4,
            mplsL3VpnVrfRteInetCidrMetric5,
            mplsL3VpnVrfRteXCPointer,
            mplsL3VpnVrfRteInetCidrStatus
       }
      STATUS  current
   ::= { mplsL3VpnGroups 8 }

   mplsL3VpnVrfRTGroup OBJECT-GROUP





      OBJECTS { mplsL3VpnVrfRTDescr,
                mplsL3VpnVrfRT,
                mplsL3VpnVrfRTRowStatus,
                mplsL3VpnVrfRTStorageType
              }
      STATUS  current
   ::= { mplsL3VpnGroups 9 }

   mplsL3VpnNotificationGroup NOTIFICATION-GROUP
       NOTIFICATIONS { mplsL3VpnVrfUp,
                       mplsL3VpnVrfDown,
                       mplsL3VpnVrfRouteMidThreshExceeded,
                       mplsL3VpnVrfNumVrfRouteMaxThreshExceeded,
                       mplsL3VpnNumVrfSecIllglLblThrshExcd,
                       mplsL3VpnNumVrfRouteMaxThreshCleared
                     }
      STATUS  current
   ::= { mplsL3VpnGroups 10 }
END

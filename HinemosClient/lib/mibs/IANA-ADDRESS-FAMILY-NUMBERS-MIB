IANA-ADDRESS-FAMILY-NUMBERS-MIB DEFINITIONS ::= BEGIN

  IMPORTS
      MODULE-IDENTITY,
      mib-2                               FROM SNMPv2-SMI
      TEXTUAL-CONVENTION                  FROM SNMPv2-TC;

  ianaAddressFamilyNumbers MODULE-IDENTITY
      LAST-UPDATED "201409020000Z"  -- September 2, 2014
      ORGANIZATION "IANA"












      ::= { mib-2 72 }


  AddressFamilyNumbers ::= TEXTUAL-CONVENTION

      STATUS       current

      SYNTAX  INTEGER {
                  other(0),
                  ipV4(1),
                  ipV6(2),
                  nsap(3),
                  hdlc(4),
                  bbn1822(5),
                  all802(6),
                  e163(7),
                  e164(8),
                  f69(9),
                  x121(10),
                  ipx(11),
                  appleTalk(12),
                  decnetIV(13),
                  banyanVines(14),
                  e164withNsap(15),
                  dns(16),
                  distinguishedName(17), -- (Distinguished Name, per X.500)
                  asNumber(18), -- (16-bit quantity, per the AS number space)
                  xtpOverIpv4(19),
                  xtpOverIpv6(20),
                  xtpNativeModeXTP(21),
                  fibreChannelWWPN(22),
                  fibreChannelWWNN(23),
                  gwid(24),
                  afi(25),
                  mplsTpSectionEndpointIdentifier(26),
                  mplsTpLspEndpointIdentifier(27),
                  mplsTpPseudowireEndpointIdentifier(28),
                  eigrpCommonServiceFamily(16384),
                  eigrpIpv4ServiceFamily(16385),
                  eigrpIpv6ServiceFamily(16386),
                  lispCanonicalAddressFormat(16387),
                  bgpLs(16388),
                  fortyeightBitMac(16389),
                  sixtyfourBitMac(16390),
                  oui(16391),
                  mac24(16392),
                  mac40(16393),
                  ipv664(16394),
                  rBridgePortID(16395),
                  trillNickname(16396),
                  reserved(65535)
              }
      END

FCIP-MGMT-MIB DEFINITIONS ::= BEGIN

   IMPORTS
       OBJECT-TYPE,
       MODULE-IDENTITY,
       Unsigned32,
       Counter32,
       mib-2               FROM SNMPv2-SMI
       TEXTUAL-CONVENTION,
       TruthValue, RowStatus, TimeStamp  FROM SNMPv2-TC
       InetAddressType,
       InetAddress,
       InetPortNumber FROM INET-ADDRESS-MIB
       FcNameIdOrZero FROM FC-MGMT-MIB
       InterfaceIndex FROM IF-MIB
       MODULE-COMPLIANCE,
       OBJECT-GROUP FROM SNMPv2-CONF
       SnmpAdminString FROM SNMP-FRAMEWORK-MIB;

   fcipMIB MODULE-IDENTITY
       LAST-UPDATED "200602060000Z"
       ORGANIZATION "IETF IPFC Working Group"
       ::= { mib-2 224 }

   fcipObjects       OBJECT IDENTIFIER ::= { fcipMIB 1 }
   fcipConformance   OBJECT IDENTIFIER ::= { fcipMIB 2 }
   fcipConfig        OBJECT IDENTIFIER ::= { fcipObjects 1 }



   FcipDomainIdInOctetForm ::= TEXTUAL-CONVENTION
       STATUS    current
       SYNTAX    OCTET STRING (SIZE(1))

   FcipEntityMode ::= TEXTUAL-CONVENTION
       STATUS current
       SYNTAX INTEGER {
                   ePortMode(1),
                   bPortMode(2)
                      }





   FcipEntityId  ::= TEXTUAL-CONVENTION
       STATUS current
       SYNTAX OCTET STRING (SIZE(8))



   fcipDynIpConfType   OBJECT-TYPE
       SYNTAX INTEGER {
                   slpv2(1),
                   none(2)
       }
       MAX-ACCESS read-write
       STATUS current
       ::= { fcipConfig 1 }

   fcipDeviceWWN   OBJECT-TYPE
       SYNTAX FcNameIdOrZero
       MAX-ACCESS read-only
       STATUS current
       ::= { fcipConfig 2 }

   fcipEntitySACKOption   OBJECT-TYPE
       SYNTAX INTEGER {
                   enabled(1),
                   disabled(2)
       }
       MAX-ACCESS read-only
       STATUS current
       ::= { fcipConfig 3 }



   fcipEntityInstanceTable OBJECT-TYPE
       SYNTAX SEQUENCE OF FcipEntityInstanceEntry
       MAX-ACCESS not-accessible
       STATUS current
       ::= { fcipConfig 4 }

   fcipEntityInstanceEntry OBJECT-TYPE
       SYNTAX FcipEntityInstanceEntry
       MAX-ACCESS not-accessible
       STATUS current
       INDEX { fcipEntityId }
       ::= { fcipEntityInstanceTable 1 }

   FcipEntityInstanceEntry ::=
       SEQUENCE {
                   fcipEntityId                  FcipEntityId,
                   fcipEntityName                SnmpAdminString,
                   fcipEntityAddressType         InetAddressType,
                   fcipEntityAddress             InetAddress,
                   fcipEntityTcpConnPort         InetPortNumber,
                   fcipEntitySeqNumWrap          TruthValue,
                   fcipEntityPHBSupport          TruthValue,
                   fcipEntityStatus              RowStatus
              }

   fcipEntityId   OBJECT-TYPE
       SYNTAX FcipEntityId
       MAX-ACCESS not-accessible





       STATUS current
       ::= { fcipEntityInstanceEntry 1 }

   fcipEntityName   OBJECT-TYPE
       SYNTAX SnmpAdminString (SIZE (0..32))
       MAX-ACCESS read-create
       STATUS current
       ::= { fcipEntityInstanceEntry 2 }

   fcipEntityAddressType   OBJECT-TYPE
       SYNTAX InetAddressType
       MAX-ACCESS read-create
       STATUS current
       ::= { fcipEntityInstanceEntry 3 }

   fcipEntityAddress   OBJECT-TYPE
       SYNTAX InetAddress
       MAX-ACCESS read-create
       STATUS current
       ::= { fcipEntityInstanceEntry 4 }

   fcipEntityTcpConnPort   OBJECT-TYPE
       SYNTAX InetPortNumber
       MAX-ACCESS read-create
       STATUS current
       DEFVAL  { 0 }
       ::= { fcipEntityInstanceEntry 5 }

   fcipEntitySeqNumWrap   OBJECT-TYPE
       SYNTAX TruthValue





       MAX-ACCESS read-only
       STATUS current
       ::= { fcipEntityInstanceEntry 6 }

   fcipEntityPHBSupport   OBJECT-TYPE
       SYNTAX TruthValue
       MAX-ACCESS read-only
       STATUS current
       ::= { fcipEntityInstanceEntry 7 }

   fcipEntityStatus   OBJECT-TYPE
       SYNTAX RowStatus
       MAX-ACCESS   read-create
       STATUS   current
       ::= { fcipEntityInstanceEntry 8 }











   fcipLinkTable OBJECT-TYPE
       SYNTAX SEQUENCE OF FcipLinkEntry
       MAX-ACCESS not-accessible
       STATUS current
       ::= { fcipConfig 5 }

   fcipLinkEntry OBJECT-TYPE
       SYNTAX FcipLinkEntry
       MAX-ACCESS not-accessible
       STATUS current
       INDEX { fcipEntityId, fcipLinkIndex }
       ::= { fcipLinkTable 1 }

   FcipLinkEntry ::=
       SEQUENCE {
                   fcipLinkIndex                       Unsigned32,
                   fcipLinkIfIndex                     InterfaceIndex,
                   fcipLinkCost                        Unsigned32,
                   fcipLinkLocalFcipEntityMode         FcipEntityMode,
                   fcipLinkLocalFcipEntityAddressType  InetAddressType,
                   fcipLinkLocalFcipEntityAddress      InetAddress,
                   fcipLinkRemFcipEntityWWN            FcNameIdOrZero,
                   fcipLinkRemFcipEntityId             FcipEntityId,
                   fcipLinkRemFcipEntityAddressType    InetAddressType,
                   fcipLinkRemFcipEntityAddress        InetAddress,
                   fcipLinkStatus                      RowStatus,
                   fcipLinkCreateTime                  TimeStamp
   }

   fcipLinkIndex     OBJECT-TYPE
       SYNTAX Unsigned32 (1..4294967295)
       MAX-ACCESS not-accessible
       STATUS current
       ::= { fcipLinkEntry 1 }





   fcipLinkIfIndex     OBJECT-TYPE
       SYNTAX InterfaceIndex
       MAX-ACCESS read-only
       STATUS current
       ::= { fcipLinkEntry 2 }

   fcipLinkCost     OBJECT-TYPE
       SYNTAX Unsigned32
       MAX-ACCESS read-create
       STATUS current
       DEFVAL  { 0 }
       ::= { fcipLinkEntry 3 }

   fcipLinkLocalFcipEntityMode   OBJECT-TYPE
       SYNTAX FcipEntityMode
       MAX-ACCESS   read-only
       STATUS   current
       ::= { fcipLinkEntry 4 }

   fcipLinkLocalFcipEntityAddressType   OBJECT-TYPE
       SYNTAX InetAddressType
       MAX-ACCESS read-create
       STATUS current
       ::= { fcipLinkEntry 5 }

   fcipLinkLocalFcipEntityAddress   OBJECT-TYPE
       SYNTAX InetAddress
       MAX-ACCESS read-create
       STATUS current
       ::= { fcipLinkEntry 6 }

   fcipLinkRemFcipEntityWWN   OBJECT-TYPE
       SYNTAX FcNameIdOrZero





       MAX-ACCESS read-create
       STATUS current
       ::= { fcipLinkEntry 7 }

   fcipLinkRemFcipEntityId   OBJECT-TYPE
       SYNTAX FcipEntityId
       MAX-ACCESS read-create
       STATUS current
       ::= { fcipLinkEntry 8 }

   fcipLinkRemFcipEntityAddressType   OBJECT-TYPE
       SYNTAX InetAddressType
       MAX-ACCESS read-create
       STATUS current
       ::= { fcipLinkEntry 9 }

   fcipLinkRemFcipEntityAddress   OBJECT-TYPE
       SYNTAX InetAddress
       MAX-ACCESS read-create
       STATUS current
       ::= { fcipLinkEntry 10 }

   fcipLinkStatus   OBJECT-TYPE
       SYNTAX RowStatus
       MAX-ACCESS   read-create
       STATUS   current
       ::= { fcipLinkEntry 11 }

   fcipLinkCreateTime OBJECT-TYPE
       SYNTAX      TimeStamp
       MAX-ACCESS  read-only
       STATUS      current
       ::= { fcipLinkEntry 12 }



   fcipTcpConnTable OBJECT-TYPE
       SYNTAX SEQUENCE OF FcipTcpConnEntry
       MAX-ACCESS not-accessible
       STATUS current
       ::= { fcipConfig 6 }

   fcipTcpConnEntry OBJECT-TYPE
       SYNTAX FcipTcpConnEntry
       MAX-ACCESS not-accessible
       STATUS current
       INDEX { fcipEntityId,
               fcipLinkIndex,
               fcipTcpConnLocalPort,
               fcipTcpConnRemPort}
       ::= { fcipTcpConnTable 1 }





   FcipTcpConnEntry ::=
       SEQUENCE {
                   fcipTcpConnLocalPort      InetPortNumber,
                   fcipTcpConnRemPort        InetPortNumber,
                   fcipTcpConnRWSize         Unsigned32,
                   fcipTcpConnMSS            Unsigned32
   }

   fcipTcpConnLocalPort     OBJECT-TYPE
       SYNTAX InetPortNumber
       MAX-ACCESS not-accessible
       STATUS current
       ::= { fcipTcpConnEntry 1 }

   fcipTcpConnRemPort     OBJECT-TYPE
       SYNTAX InetPortNumber
       MAX-ACCESS not-accessible
       STATUS current
       ::= { fcipTcpConnEntry 2 }

   fcipTcpConnRWSize     OBJECT-TYPE
       SYNTAX Unsigned32
       MAX-ACCESS read-only
       STATUS current
       ::= { fcipTcpConnEntry 3 }

   fcipTcpConnMSS     OBJECT-TYPE
       SYNTAX Unsigned32
       MAX-ACCESS read-only
       STATUS current
       ::= { fcipTcpConnEntry 4 }














   fcipDynamicRouteTable OBJECT-TYPE
       SYNTAX SEQUENCE OF FcipDynamicRouteEntry
       MAX-ACCESS not-accessible
       STATUS current
       ::= { fcipConfig 7 }

   fcipDynamicRouteEntry OBJECT-TYPE
       SYNTAX FcipDynamicRouteEntry
       MAX-ACCESS not-accessible
       STATUS current
       INDEX { fcipEntityId, fcipDynamicRouteDID }
       ::= { fcipDynamicRouteTable 1 }

   FcipDynamicRouteEntry ::=
       SEQUENCE {
                   fcipDynamicRouteDID          FcipDomainIdInOctetForm,
                   fcipDynamicRouteLinkIndex    Unsigned32
               }

   fcipDynamicRouteDID    OBJECT-TYPE
       SYNTAX FcipDomainIdInOctetForm
       MAX-ACCESS not-accessible
       STATUS current
       ::= { fcipDynamicRouteEntry  1 }

   fcipDynamicRouteLinkIndex    OBJECT-TYPE
       SYNTAX Unsigned32 (1..4294967295)
       MAX-ACCESS read-only
       STATUS current
       ::= { fcipDynamicRouteEntry  2 }



   fcipStaticRouteTable OBJECT-TYPE
       SYNTAX SEQUENCE OF FcipStaticRouteEntry
       MAX-ACCESS not-accessible
       STATUS current
       ::= { fcipConfig 8 }

   fcipStaticRouteEntry OBJECT-TYPE
       SYNTAX FcipStaticRouteEntry
       MAX-ACCESS not-accessible
       STATUS current
       INDEX { fcipEntityId, fcipStaticRouteDID }
       ::= { fcipStaticRouteTable 1 }

   FcipStaticRouteEntry ::=
       SEQUENCE {
                   fcipStaticRouteDID           FcipDomainIdInOctetForm,
                   fcipStaticRouteLinkIndex     Unsigned32,
                   fcipStaticRouteStatus        RowStatus
               }

   fcipStaticRouteDID    OBJECT-TYPE
       SYNTAX FcipDomainIdInOctetForm





       MAX-ACCESS not-accessible
       STATUS current
       ::= { fcipStaticRouteEntry  1 }

   fcipStaticRouteLinkIndex    OBJECT-TYPE
       SYNTAX Unsigned32 (1..4294967295)
       MAX-ACCESS read-create
       STATUS current
       ::= { fcipStaticRouteEntry  2 }

   fcipStaticRouteStatus   OBJECT-TYPE
       SYNTAX RowStatus
       MAX-ACCESS   read-create
       STATUS   current
       ::= { fcipStaticRouteEntry  3 }



   fcipDiscoveryDomainTable OBJECT-TYPE
       SYNTAX SEQUENCE OF FcipDiscoveryDomainEntry
       MAX-ACCESS not-accessible
       STATUS current
       ::= { fcipConfig 9 }





   fcipDiscoveryDomainEntry OBJECT-TYPE
       SYNTAX FcipDiscoveryDomainEntry
       MAX-ACCESS not-accessible
       STATUS current
       INDEX { fcipEntityId, fcipDiscoveryDomainIndex }
       ::= { fcipDiscoveryDomainTable 1 }

   FcipDiscoveryDomainEntry ::=
       SEQUENCE {
           fcipDiscoveryDomainIndex        Unsigned32,
           fcipDiscoveryDomainName         SnmpAdminString
       }

   fcipDiscoveryDomainIndex OBJECT-TYPE
       SYNTAX     Unsigned32 (1..4294967295)
       MAX-ACCESS not-accessible
       STATUS     current
       ::= { fcipDiscoveryDomainEntry 1 }

   fcipDiscoveryDomainName   OBJECT-TYPE
       SYNTAX SnmpAdminString (SIZE (0..128))
       MAX-ACCESS read-write
       STATUS current
       ::= { fcipDiscoveryDomainEntry 2 }

















   fcipLinkErrorsTable OBJECT-TYPE
       SYNTAX SEQUENCE OF FcipLinkErrorsEntry
       MAX-ACCESS not-accessible
       STATUS current
       ::= { fcipConfig 10 }

   fcipLinkErrorsEntry OBJECT-TYPE
       SYNTAX FcipLinkErrorsEntry
       MAX-ACCESS not-accessible
       STATUS current
       INDEX { fcipEntityId, fcipLinkIndex }
       ::= { fcipLinkErrorsTable 1 }

   FcipLinkErrorsEntry ::=
       SEQUENCE {
           fcipLinkFcipLossofFcSynchs            Counter32,
           fcipLinkFcipEncapErrors               Counter32,
           fcipLinkFcipNotReceivedSfResps        Counter32,
           fcipLinkFcipSfRespMismatches          Counter32,
           fcipLinkFcipSfInvalidNonces           Counter32,
           fcipLinkFcipReceivedSfDuplicates      Counter32,
           fcipLinkFcipSfInvalidWWNs             Counter32,
           fcipLinkFcipBB2LkaTimeOuts            Counter32,
           fcipLinkFcipSntpExpiredTimeStamps     Counter32,
           fcipLinkTcpTooManyErrors              Counter32,
           fcipLinkTcpExcessiveDroppedDatagrams  Counter32,
           fcipLinkTcpSaParamMismatches          Counter32
       }

   fcipLinkFcipLossofFcSynchs OBJECT-TYPE
       SYNTAX     Counter32
       MAX-ACCESS read-only
       STATUS     current
       ::= { fcipLinkErrorsEntry 1 }

   fcipLinkFcipEncapErrors OBJECT-TYPE
       SYNTAX     Counter32
       MAX-ACCESS read-only
       STATUS     current
       ::= { fcipLinkErrorsEntry 2 }

   fcipLinkFcipNotReceivedSfResps OBJECT-TYPE
       SYNTAX     Counter32
       MAX-ACCESS read-only
       STATUS     current
       ::= { fcipLinkErrorsEntry 3 }

   fcipLinkFcipSfRespMismatches OBJECT-TYPE
       SYNTAX     Counter32
       MAX-ACCESS read-only
       STATUS     current
       ::= { fcipLinkErrorsEntry 4 }

   fcipLinkFcipSfInvalidNonces OBJECT-TYPE
       SYNTAX     Counter32
       MAX-ACCESS read-only
       STATUS     current
       ::= { fcipLinkErrorsEntry 5 }

   fcipLinkFcipReceivedSfDuplicates OBJECT-TYPE
       SYNTAX     Counter32





       MAX-ACCESS read-only
       STATUS     current
       ::= { fcipLinkErrorsEntry 6 }

   fcipLinkFcipSfInvalidWWNs OBJECT-TYPE
       SYNTAX     Counter32
       MAX-ACCESS read-only
       STATUS     current
       ::= { fcipLinkErrorsEntry 7 }

   fcipLinkFcipBB2LkaTimeOuts OBJECT-TYPE
       SYNTAX     Counter32
       MAX-ACCESS read-only
       STATUS     current
       ::= { fcipLinkErrorsEntry 8 }

   fcipLinkFcipSntpExpiredTimeStamps OBJECT-TYPE
       SYNTAX     Counter32
       MAX-ACCESS read-only
       STATUS     current
       ::= { fcipLinkErrorsEntry 9 }

   fcipLinkTcpTooManyErrors OBJECT-TYPE
       SYNTAX     Counter32
       MAX-ACCESS read-only
       STATUS     current
       ::= { fcipLinkErrorsEntry 10  }

   fcipLinkTcpExcessiveDroppedDatagrams OBJECT-TYPE
       SYNTAX     Counter32
       MAX-ACCESS read-only
       STATUS     current
       ::= { fcipLinkErrorsEntry 11  }

   fcipLinkTcpSaParamMismatches OBJECT-TYPE
       SYNTAX     Counter32
       MAX-ACCESS read-only
       STATUS     current
       ::= { fcipLinkErrorsEntry 12  }



   fcipCompliances   OBJECT IDENTIFIER ::= { fcipConformance 1 }
   fcipGroups        OBJECT IDENTIFIER ::= { fcipConformance 2 }

   fcipCompliance MODULE-COMPLIANCE
       STATUS current
       MODULE       -- this module
           MANDATORY-GROUPS {
               fcipEntityScalarGroup,
               fcipEntityInstanceGroup,
               fcipLinkGroup,
               fcipTcpConnGroup,
               fcipDiscoveryDomainGroup,
               fcipLinkErrorsGroup





           }

           GROUP   fcipDynamicRouteGroup

           GROUP   fcipStaticRouteGroup

          OBJECT   fcipEntityAddressType
          SYNTAX   INTEGER { ipv4(1), ipv6(2) }

          OBJECT   fcipEntityAddress
          SYNTAX   InetAddress (SIZE(4|16))

          OBJECT   fcipLinkLocalFcipEntityAddressType
          SYNTAX   INTEGER { ipv4(1), ipv6(2) }

          OBJECT   fcipLinkLocalFcipEntityAddress
          SYNTAX   InetAddress (SIZE(4|16))

          OBJECT   fcipLinkRemFcipEntityAddressType
          SYNTAX   INTEGER { ipv4(1), ipv6(2) }

          OBJECT   fcipLinkRemFcipEntityAddress
          SYNTAX   InetAddress (SIZE(4|16))






       ::= { fcipCompliances 1 }

   fcipEntityScalarGroup OBJECT-GROUP
       OBJECTS {   fcipDynIpConfType,
                   fcipDeviceWWN,
                   fcipEntitySACKOption
       }
       STATUS current
   ::= { fcipGroups 1 }

   fcipEntityInstanceGroup OBJECT-GROUP
       OBJECTS {
                   fcipEntityName,
                   fcipEntityAddressType,
                   fcipEntityAddress,
                   fcipEntityTcpConnPort,
                   fcipEntitySeqNumWrap,
                   fcipEntityPHBSupport,
                   fcipEntityStatus
       }
       STATUS current
   ::= { fcipGroups 2 }

   fcipLinkGroup OBJECT-GROUP
       OBJECTS {
                   fcipLinkIfIndex,
                   fcipLinkCost,
                   fcipLinkLocalFcipEntityMode,
                   fcipLinkLocalFcipEntityAddressType,
                   fcipLinkLocalFcipEntityAddress,
                   fcipLinkRemFcipEntityWWN,
                   fcipLinkRemFcipEntityId,
                   fcipLinkRemFcipEntityAddressType,
                   fcipLinkRemFcipEntityAddress,
                   fcipLinkStatus,
                   fcipLinkCreateTime
       }





       STATUS current
   ::= { fcipGroups 3 }

   fcipTcpConnGroup OBJECT-GROUP
       OBJECTS {
                   fcipTcpConnRWSize,
                   fcipTcpConnMSS
       }
       STATUS current
   ::= { fcipGroups 4 }

   fcipDiscoveryDomainGroup OBJECT-GROUP
       OBJECTS {
                   fcipDiscoveryDomainName
       }
       STATUS current
   ::= { fcipGroups 5 }

   fcipLinkErrorsGroup OBJECT-GROUP
       OBJECTS {
           fcipLinkFcipLossofFcSynchs,
           fcipLinkFcipEncapErrors,
           fcipLinkFcipNotReceivedSfResps,
           fcipLinkFcipSfRespMismatches,
           fcipLinkFcipSfInvalidNonces,
           fcipLinkFcipReceivedSfDuplicates,
           fcipLinkFcipSfInvalidWWNs,
           fcipLinkFcipBB2LkaTimeOuts,
           fcipLinkFcipSntpExpiredTimeStamps,
           fcipLinkTcpTooManyErrors,
           fcipLinkTcpExcessiveDroppedDatagrams,
           fcipLinkTcpSaParamMismatches
       }
       STATUS current
   ::= { fcipGroups 6 }






   fcipDynamicRouteGroup OBJECT-GROUP
       OBJECTS {
                   fcipDynamicRouteLinkIndex
       }
       STATUS current
   ::= { fcipGroups 7 }

   fcipStaticRouteGroup OBJECT-GROUP
       OBJECTS {
                   fcipStaticRouteLinkIndex,
                   fcipStaticRouteStatus
       }
       STATUS current
   ::= { fcipGroups 8 }

   END

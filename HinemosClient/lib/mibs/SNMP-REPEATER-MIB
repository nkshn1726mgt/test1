SNMP-REPEATER-MIB DEFINITIONS ::= BEGIN

   IMPORTS
       Counter32, Counter64, Integer32, Gauge32, TimeTicks,
       OBJECT-TYPE, MODULE-IDENTITY, NOTIFICATION-TYPE, mib-2
           FROM SNMPv2-SMI
       TimeStamp, DisplayString, MacAddress, TEXTUAL-CONVENTION,
       RowStatus, TestAndIncr
           FROM SNMPv2-TC
       OBJECT-GROUP, MODULE-COMPLIANCE
           FROM SNMPv2-CONF
       OwnerString
           FROM IF-MIB;


   snmpRptrMod MODULE-IDENTITY
       LAST-UPDATED    "9609140000Z"
       ORGANIZATION    "IETF HUB MIB Working Group"
       ::= { snmpDot3RptrMgt 5 }



   snmpDot3RptrMgt OBJECT IDENTIFIER ::= { mib-2 22 }


   OptMacAddr ::= TEXTUAL-CONVENTION
       DISPLAY-HINT    "1x:"
       STATUS          current
       SYNTAX OCTET STRING (SIZE (0 | 6))




   rptrBasicPackage
       OBJECT IDENTIFIER ::= { snmpDot3RptrMgt 1 }
     rptrRptrInfo
           OBJECT IDENTIFIER ::= { rptrBasicPackage 1 }
     rptrGroupInfo





           OBJECT IDENTIFIER ::= { rptrBasicPackage 2 }
     rptrPortInfo
           OBJECT IDENTIFIER ::= { rptrBasicPackage 3 }
     rptrAllRptrInfo
           OBJECT IDENTIFIER ::= { rptrBasicPackage 4 }

   rptrMonitorPackage
       OBJECT IDENTIFIER ::= { snmpDot3RptrMgt 2 }
     rptrMonitorRptrInfo
           OBJECT IDENTIFIER ::= { rptrMonitorPackage 1 }
     rptrMonitorGroupInfo
           OBJECT IDENTIFIER ::= { rptrMonitorPackage 2 }
     rptrMonitorPortInfo
           OBJECT IDENTIFIER ::= { rptrMonitorPackage 3 }
     rptrMonitorAllRptrInfo
           OBJECT IDENTIFIER ::= { rptrMonitorPackage 4 }

   rptrAddrTrackPackage
       OBJECT IDENTIFIER ::= { snmpDot3RptrMgt 3 }
     rptrAddrTrackRptrInfo
           OBJECT IDENTIFIER ::= { rptrAddrTrackPackage 1 }
     rptrAddrTrackGroupInfo
           OBJECT IDENTIFIER ::= { rptrAddrTrackPackage 2 }
     rptrAddrTrackPortInfo
           OBJECT IDENTIFIER ::= { rptrAddrTrackPackage 3 }

   rptrTopNPackage
           OBJECT IDENTIFIER ::= { snmpDot3RptrMgt 4 }
     rptrTopNRptrInfo
           OBJECT IDENTIFIER ::= { rptrTopNPackage 1 }
     rptrTopNGroupInfo
           OBJECT IDENTIFIER ::= { rptrTopNPackage 2 }
     rptrTopNPortInfo
           OBJECT IDENTIFIER ::= { rptrTopNPackage 3 }








   rptrGroupCapacity OBJECT-TYPE
       SYNTAX      Integer32 (1..2147483647)
       MAX-ACCESS  read-only
       STATUS      deprecated
       ::= { rptrRptrInfo 1 }

   rptrOperStatus OBJECT-TYPE
       SYNTAX      INTEGER {
                     other(1),            -- undefined or unknown
                     ok(2),               -- no known failures
                     rptrFailure(3),      -- repeater-related failure
                     groupFailure(4),     -- group-related failure
                     portFailure(5),      -- port-related failure
                     generalFailure(6)    -- failure, unspecified type





                   }
       MAX-ACCESS  read-only
       STATUS      deprecated
       ::= { rptrRptrInfo 2 }

   rptrHealthText OBJECT-TYPE
       SYNTAX      DisplayString (SIZE (0..255))
       MAX-ACCESS  read-only
       STATUS      deprecated
       ::= { rptrRptrInfo 3 }

   rptrReset OBJECT-TYPE
       SYNTAX      INTEGER {
                     noReset(1),
                     reset(2)





                   }
       MAX-ACCESS  read-write
       STATUS      deprecated
       ::= { rptrRptrInfo 4 }

   rptrNonDisruptTest OBJECT-TYPE
       SYNTAX      INTEGER {
                     noSelfTest(1),
                     selfTest(2)





                   }
       MAX-ACCESS  read-write
       STATUS      deprecated
       ::= { rptrRptrInfo 5 }

   rptrTotalPartitionedPorts OBJECT-TYPE
       SYNTAX      Gauge32
       MAX-ACCESS  read-only
       STATUS      deprecated
       ::= { rptrRptrInfo 6 }







   rptrGroupTable OBJECT-TYPE
       SYNTAX      SEQUENCE OF RptrGroupEntry
       MAX-ACCESS  not-accessible
       STATUS      current
       ::= { rptrGroupInfo 1 }

   rptrGroupEntry OBJECT-TYPE
       SYNTAX      RptrGroupEntry
       MAX-ACCESS  not-accessible
       STATUS      current
       INDEX    { rptrGroupIndex }
       ::= { rptrGroupTable 1 }

   RptrGroupEntry ::=
       SEQUENCE {
           rptrGroupIndex
               Integer32,
           rptrGroupDescr
               DisplayString,
           rptrGroupObjectID
               OBJECT IDENTIFIER,
           rptrGroupOperStatus
               INTEGER,
           rptrGroupLastOperStatusChange
               TimeTicks,
           rptrGroupPortCapacity
               Integer32
       }

   rptrGroupIndex OBJECT-TYPE
       SYNTAX      Integer32 (1..2147483647)
       MAX-ACCESS  read-only
       STATUS      current
       ::= { rptrGroupEntry 1 }

   rptrGroupDescr OBJECT-TYPE
       SYNTAX      DisplayString (SIZE (0..255))
       MAX-ACCESS  read-only
       STATUS      deprecated
       ::= { rptrGroupEntry 2 }

   rptrGroupObjectID OBJECT-TYPE
       SYNTAX      OBJECT IDENTIFIER
       MAX-ACCESS  read-only
       STATUS      current
       ::= { rptrGroupEntry 3 }

   rptrGroupOperStatus OBJECT-TYPE
       SYNTAX      INTEGER {
                     other(1),





                     operational(2),
                     malfunctioning(3),
                     notPresent(4),
                     underTest(5),
                     resetInProgress(6)
                   }
       MAX-ACCESS  read-only
       STATUS      current
       ::= { rptrGroupEntry 4 }

   rptrGroupLastOperStatusChange OBJECT-TYPE
       SYNTAX      TimeTicks
       MAX-ACCESS  read-only
       STATUS      deprecated
       ::= { rptrGroupEntry 5 }

   rptrGroupPortCapacity OBJECT-TYPE
       SYNTAX      Integer32 (1..2147483647)
       MAX-ACCESS  read-only





       STATUS      current
       ::= { rptrGroupEntry 6 }



   rptrPortTable OBJECT-TYPE
       SYNTAX      SEQUENCE OF RptrPortEntry
       MAX-ACCESS  not-accessible
       STATUS      current
       ::= { rptrPortInfo 1 }

   rptrPortEntry OBJECT-TYPE
       SYNTAX      RptrPortEntry
       MAX-ACCESS  not-accessible
       STATUS      current





       INDEX    { rptrPortGroupIndex, rptrPortIndex }
       ::= { rptrPortTable 1 }

   RptrPortEntry ::=
       SEQUENCE {
           rptrPortGroupIndex
               Integer32,
           rptrPortIndex
               Integer32,
           rptrPortAdminStatus
               INTEGER,
           rptrPortAutoPartitionState
               INTEGER,
           rptrPortOperStatus
               INTEGER,
           rptrPortRptrId
               Integer32
       }

   rptrPortGroupIndex OBJECT-TYPE
       SYNTAX      Integer32 (1..2147483647)
       MAX-ACCESS  read-only
       STATUS      current
       ::= { rptrPortEntry 1 }

   rptrPortIndex OBJECT-TYPE
       SYNTAX      Integer32 (1..2147483647)
       MAX-ACCESS  read-only
       STATUS      current
       ::= { rptrPortEntry 2 }

   rptrPortAdminStatus OBJECT-TYPE
       SYNTAX      INTEGER {
                     enabled(1),
                     disabled(2)





                   }
       MAX-ACCESS  read-write
       STATUS      current
       ::= { rptrPortEntry 3 }

   rptrPortAutoPartitionState OBJECT-TYPE
       SYNTAX      INTEGER {
                     notAutoPartitioned(1),
                     autoPartitioned(2)
                   }
       MAX-ACCESS  read-only
       STATUS      current
       ::= { rptrPortEntry 4 }

   rptrPortOperStatus  OBJECT-TYPE
       SYNTAX      INTEGER {
                     operational(1),
                     notOperational(2),
                     notPresent(3)
                   }
       MAX-ACCESS  read-only
       STATUS      current
       ::= { rptrPortEntry 5 }

   rptrPortRptrId OBJECT-TYPE
       SYNTAX      Integer32 (0..2147483647)
       MAX-ACCESS  read-only
       STATUS      current
       ::= { rptrPortEntry 6 }



   rptrInfoTable OBJECT-TYPE





       SYNTAX      SEQUENCE OF RptrInfoEntry
       MAX-ACCESS  not-accessible
       STATUS      current
       ::= { rptrAllRptrInfo 1 }

   rptrInfoEntry OBJECT-TYPE
       SYNTAX      RptrInfoEntry
       MAX-ACCESS  not-accessible
       STATUS      current
       INDEX    { rptrInfoId }
       ::= { rptrInfoTable 1 }

   RptrInfoEntry ::=
       SEQUENCE {
           rptrInfoId
               Integer32,
           rptrInfoRptrType
               INTEGER,
           rptrInfoOperStatus
               INTEGER,
           rptrInfoReset
               INTEGER,
           rptrInfoPartitionedPorts
               Gauge32,
           rptrInfoLastChange
               TimeStamp
       }

   rptrInfoId OBJECT-TYPE
       SYNTAX      Integer32 (1..2147483647)
       MAX-ACCESS  read-only
       STATUS      current
       ::= { rptrInfoEntry 1 }

   rptrInfoRptrType OBJECT-TYPE
       SYNTAX      INTEGER {
                     other(1),                -- undefined or unknown





                     tenMb(2),
                     onehundredMbClassI(3),
                     onehundredMbClassII(4)
                   }
       MAX-ACCESS  read-only
       STATUS      current
       ::= { rptrInfoEntry 2 }

   rptrInfoOperStatus OBJECT-TYPE
       SYNTAX      INTEGER {
                     other(1),
                     ok(2),
                     failure(3)
                   }
       MAX-ACCESS  read-only
       STATUS      current
       ::= { rptrInfoEntry 3 }

   rptrInfoReset OBJECT-TYPE
       SYNTAX      INTEGER {
                     noReset(1),
                     reset(2)
                   }
       MAX-ACCESS  read-write
       STATUS      current
       ::= { rptrInfoEntry 4 }

   rptrInfoPartitionedPorts OBJECT-TYPE
       SYNTAX      Gauge32
       MAX-ACCESS  read-only
       STATUS      current
       ::= { rptrInfoEntry 5 }

   rptrInfoLastChange OBJECT-TYPE
       SYNTAX      TimeStamp
       MAX-ACCESS  read-only
       STATUS      current
       ::= { rptrInfoEntry 6 }







   rptrMonitorTransmitCollisions OBJECT-TYPE
       SYNTAX      Counter32
       MAX-ACCESS  read-only
       STATUS      deprecated
       ::= { rptrMonitorRptrInfo 1 }



   rptrMonitorGroupTable OBJECT-TYPE
       SYNTAX      SEQUENCE OF RptrMonitorGroupEntry
       MAX-ACCESS  not-accessible
       STATUS      deprecated
       ::= { rptrMonitorGroupInfo 1 }

   rptrMonitorGroupEntry OBJECT-TYPE
       SYNTAX    RptrMonitorGroupEntry
       MAX-ACCESS  not-accessible
       STATUS    deprecated
       INDEX    { rptrMonitorGroupIndex }
       ::= { rptrMonitorGroupTable 1 }

   RptrMonitorGroupEntry ::=
       SEQUENCE {
           rptrMonitorGroupIndex
               Integer32,
           rptrMonitorGroupTotalFrames
               Counter32,
           rptrMonitorGroupTotalOctets
               Counter32,
           rptrMonitorGroupTotalErrors
               Counter32
       }

   rptrMonitorGroupIndex OBJECT-TYPE
       SYNTAX      Integer32 (1..2147483647)
       MAX-ACCESS  read-only
       STATUS      deprecated
       ::= { rptrMonitorGroupEntry 1 }

   rptrMonitorGroupTotalFrames OBJECT-TYPE
       SYNTAX      Counter32
       MAX-ACCESS  read-only
       STATUS      deprecated
       ::= { rptrMonitorGroupEntry 2 }

   rptrMonitorGroupTotalOctets OBJECT-TYPE
       SYNTAX      Counter32
       MAX-ACCESS  read-only
       STATUS      deprecated
       ::= { rptrMonitorGroupEntry 3 }

   rptrMonitorGroupTotalErrors OBJECT-TYPE
       SYNTAX      Counter32
       MAX-ACCESS  read-only
       STATUS      deprecated
       ::= { rptrMonitorGroupEntry 4 }



   rptrMonitorPortTable OBJECT-TYPE
       SYNTAX      SEQUENCE OF RptrMonitorPortEntry
       MAX-ACCESS  not-accessible
       STATUS      current
       ::= { rptrMonitorPortInfo 1 }

   rptrMonitorPortEntry OBJECT-TYPE
       SYNTAX      RptrMonitorPortEntry
       MAX-ACCESS  not-accessible
       STATUS      current
       INDEX    { rptrMonitorPortGroupIndex, rptrMonitorPortIndex }
       ::= { rptrMonitorPortTable 1 }

   RptrMonitorPortEntry ::=
       SEQUENCE {
           rptrMonitorPortGroupIndex
               Integer32,
           rptrMonitorPortIndex
               Integer32,
           rptrMonitorPortReadableFrames
               Counter32,
           rptrMonitorPortReadableOctets
               Counter32,
           rptrMonitorPortFCSErrors
               Counter32,
           rptrMonitorPortAlignmentErrors
               Counter32,
           rptrMonitorPortFrameTooLongs
               Counter32,
           rptrMonitorPortShortEvents
               Counter32,
           rptrMonitorPortRunts
               Counter32,
           rptrMonitorPortCollisions
               Counter32,
           rptrMonitorPortLateEvents
               Counter32,
           rptrMonitorPortVeryLongEvents
               Counter32,
           rptrMonitorPortDataRateMismatches
               Counter32,
           rptrMonitorPortAutoPartitions
               Counter32,
           rptrMonitorPortTotalErrors





               Counter32,
           rptrMonitorPortLastChange
               TimeStamp
       }

   rptrMonitorPortGroupIndex OBJECT-TYPE
       SYNTAX      Integer32 (1..2147483647)
       MAX-ACCESS  read-only
       STATUS      current
       ::= { rptrMonitorPortEntry 1 }

   rptrMonitorPortIndex OBJECT-TYPE
       SYNTAX      Integer32 (1..2147483647)
       MAX-ACCESS  read-only
       STATUS      current
       ::= { rptrMonitorPortEntry 2 }

   rptrMonitorPortReadableFrames OBJECT-TYPE
       SYNTAX      Counter32
       MAX-ACCESS  read-only
       STATUS      current
       ::= { rptrMonitorPortEntry 3 }

   rptrMonitorPortReadableOctets OBJECT-TYPE
       SYNTAX      Counter32
       MAX-ACCESS  read-only
       STATUS      current
       ::= { rptrMonitorPortEntry 4 }

   rptrMonitorPortFCSErrors OBJECT-TYPE
       SYNTAX      Counter32
       MAX-ACCESS  read-only
       STATUS      current
       ::= { rptrMonitorPortEntry 5 }

   rptrMonitorPortAlignmentErrors OBJECT-TYPE
       SYNTAX      Counter32
       MAX-ACCESS  read-only
       STATUS      current
       ::= { rptrMonitorPortEntry 6 }

   rptrMonitorPortFrameTooLongs OBJECT-TYPE
       SYNTAX      Counter32
       MAX-ACCESS  read-only
       STATUS      current
       ::= { rptrMonitorPortEntry 7 }

   rptrMonitorPortShortEvents OBJECT-TYPE
       SYNTAX      Counter32
       MAX-ACCESS  read-only
       STATUS      current
       ::= { rptrMonitorPortEntry 8 }

   rptrMonitorPortRunts OBJECT-TYPE
       SYNTAX      Counter32
       MAX-ACCESS  read-only
       STATUS      current
       ::= { rptrMonitorPortEntry 9 }

   rptrMonitorPortCollisions OBJECT-TYPE
       SYNTAX      Counter32
       MAX-ACCESS  read-only
       STATUS      current
       ::= { rptrMonitorPortEntry 10 }

   rptrMonitorPortLateEvents OBJECT-TYPE
       SYNTAX      Counter32
       MAX-ACCESS  read-only
       STATUS      current
       ::= { rptrMonitorPortEntry 11 }

   rptrMonitorPortVeryLongEvents OBJECT-TYPE
       SYNTAX      Counter32
       MAX-ACCESS  read-only
       STATUS      current
       ::= { rptrMonitorPortEntry 12 }

   rptrMonitorPortDataRateMismatches OBJECT-TYPE





       SYNTAX      Counter32
       MAX-ACCESS  read-only
       STATUS      current
       ::= { rptrMonitorPortEntry 13 }

   rptrMonitorPortAutoPartitions OBJECT-TYPE
       SYNTAX      Counter32
       MAX-ACCESS  read-only





       STATUS      current
       ::= { rptrMonitorPortEntry 14 }

   rptrMonitorPortTotalErrors OBJECT-TYPE
       SYNTAX      Counter32
       MAX-ACCESS  read-only
       STATUS      current
       ::= { rptrMonitorPortEntry 15 }

   rptrMonitorPortLastChange OBJECT-TYPE
       SYNTAX      TimeStamp
       MAX-ACCESS  read-only
       STATUS      current
       ::= { rptrMonitorPortEntry 16 }

   rptrMonitor100PortTable OBJECT-TYPE
       SYNTAX      SEQUENCE OF RptrMonitor100PortEntry
       MAX-ACCESS  not-accessible
       STATUS      current
       ::= { rptrMonitorPortInfo 2 }

   rptrMonitor100PortEntry OBJECT-TYPE
       SYNTAX      RptrMonitor100PortEntry
       MAX-ACCESS  not-accessible
       STATUS      current





       INDEX    { rptrMonitorPortGroupIndex, rptrMonitorPortIndex }
       ::= { rptrMonitor100PortTable 1 }

   RptrMonitor100PortEntry ::=
       SEQUENCE {
           rptrMonitorPortIsolates
               Counter32,
           rptrMonitorPortSymbolErrors
               Counter32,
           rptrMonitorPortUpper32Octets
               Counter32,
           rptrMonitorPortHCReadableOctets
               Counter64
       }

   rptrMonitorPortIsolates OBJECT-TYPE
       SYNTAX      Counter32
       MAX-ACCESS  read-only
       STATUS      current
       ::= { rptrMonitor100PortEntry 1 }

   rptrMonitorPortSymbolErrors OBJECT-TYPE
       SYNTAX      Counter32
       MAX-ACCESS  read-only
       STATUS      current
       ::= { rptrMonitor100PortEntry 2 }

   rptrMonitorPortUpper32Octets OBJECT-TYPE
       SYNTAX      Counter32
       MAX-ACCESS  read-only
       STATUS      current





       ::= { rptrMonitor100PortEntry 3 }

   rptrMonitorPortHCReadableOctets OBJECT-TYPE
       SYNTAX      Counter64
       MAX-ACCESS  read-only
       STATUS      current
       ::= { rptrMonitor100PortEntry 4 }



   rptrMonTable OBJECT-TYPE
       SYNTAX      SEQUENCE OF RptrMonEntry





       MAX-ACCESS  not-accessible
       STATUS      current
       ::= { rptrMonitorAllRptrInfo 1 }

   rptrMonEntry OBJECT-TYPE
       SYNTAX      RptrMonEntry
       MAX-ACCESS  not-accessible
       STATUS      current
       INDEX    { rptrInfoId }
       ::= { rptrMonTable 1 }

   RptrMonEntry ::=
       SEQUENCE {
           rptrMonTxCollisions
               Counter32,
           rptrMonTotalFrames
               Counter32,
           rptrMonTotalErrors
               Counter32,
           rptrMonTotalOctets
               Counter32
       }

   rptrMonTxCollisions OBJECT-TYPE
       SYNTAX      Counter32
       MAX-ACCESS  read-only
       STATUS      current
       ::= { rptrMonEntry 1 }

   rptrMonTotalFrames OBJECT-TYPE
       SYNTAX      Counter32
       MAX-ACCESS  read-only
       STATUS      current
       ::= { rptrMonEntry 3 }

   rptrMonTotalErrors OBJECT-TYPE
       SYNTAX      Counter32
       MAX-ACCESS  read-only
       STATUS      current
       ::= { rptrMonEntry 4 }

   rptrMonTotalOctets OBJECT-TYPE





       SYNTAX      Counter32
       MAX-ACCESS  read-only
       STATUS      current
       ::= { rptrMonEntry 5 }

   rptrMon100Table OBJECT-TYPE
       SYNTAX      SEQUENCE OF RptrMon100Entry
       MAX-ACCESS  not-accessible
       STATUS      current
       ::= { rptrMonitorAllRptrInfo 2 }

   rptrMon100Entry OBJECT-TYPE
       SYNTAX      RptrMon100Entry
       MAX-ACCESS  not-accessible





       STATUS      current
       INDEX    { rptrInfoId }
       ::= { rptrMon100Table 1 }

   RptrMon100Entry ::=
       SEQUENCE {
           rptrMonUpper32TotalOctets
               Counter32,
           rptrMonHCTotalOctets
               Counter64
       }

   rptrMonUpper32TotalOctets OBJECT-TYPE
       SYNTAX      Counter32
       MAX-ACCESS  read-only
       STATUS      current
       ::= { rptrMon100Entry 1 }

   rptrMonHCTotalOctets OBJECT-TYPE
       SYNTAX      Counter64
       MAX-ACCESS  read-only
       STATUS      current
       ::= { rptrMon100Entry 2 }








   rptrAddrSearchTable OBJECT-TYPE
       SYNTAX     SEQUENCE OF RptrAddrSearchEntry
       MAX-ACCESS not-accessible
       STATUS     current
       ::= { rptrAddrTrackRptrInfo 1 }

   rptrAddrSearchEntry OBJECT-TYPE
       SYNTAX     RptrAddrSearchEntry
       MAX-ACCESS not-accessible
       STATUS     current
       INDEX      { rptrInfoId }
       ::= { rptrAddrSearchTable 1 }

   RptrAddrSearchEntry ::=
       SEQUENCE {
           rptrAddrSearchLock     TestAndIncr,
           rptrAddrSearchStatus   INTEGER,
           rptrAddrSearchAddress  MacAddress,
           rptrAddrSearchState    INTEGER,
           rptrAddrSearchGroup    Integer32,
           rptrAddrSearchPort     Integer32,
           rptrAddrSearchOwner    OwnerString
       }


   rptrAddrSearchLock OBJECT-TYPE
       SYNTAX     TestAndIncr
       MAX-ACCESS read-write
       STATUS     current
       ::= { rptrAddrSearchEntry 1 }

   rptrAddrSearchStatus  OBJECT-TYPE
       SYNTAX     INTEGER {
                      notInUse(1),
                      inUse(2)
                  }
       MAX-ACCESS read-write
       STATUS     current
       ::= { rptrAddrSearchEntry 2 }

   rptrAddrSearchAddress OBJECT-TYPE
       SYNTAX     MacAddress
       MAX-ACCESS read-write
       STATUS     current
       ::= { rptrAddrSearchEntry 3 }

   rptrAddrSearchState OBJECT-TYPE
       SYNTAX     INTEGER {
                       none(1),
                       single(2),
                       multiple(3)
                  }
       MAX-ACCESS read-only
       STATUS     current
       ::= { rptrAddrSearchEntry 4 }

   rptrAddrSearchGroup OBJECT-TYPE
       SYNTAX     Integer32 (0..2147483647)
       MAX-ACCESS read-only
       STATUS     current
       ::= { rptrAddrSearchEntry 5 }

   rptrAddrSearchPort OBJECT-TYPE
       SYNTAX     Integer32 (0..2147483647)
       MAX-ACCESS read-only
       STATUS     current
       ::= { rptrAddrSearchEntry 6 }

   rptrAddrSearchOwner OBJECT-TYPE
       SYNTAX     OwnerString
       MAX-ACCESS read-write
       STATUS     current
       ::= { rptrAddrSearchEntry 7 }



   rptrAddrTrackTable OBJECT-TYPE
       SYNTAX      SEQUENCE OF RptrAddrTrackEntry
       MAX-ACCESS  not-accessible
       STATUS      current
       ::= { rptrAddrTrackPortInfo 1 }

   rptrAddrTrackEntry OBJECT-TYPE
       SYNTAX      RptrAddrTrackEntry
       MAX-ACCESS  not-accessible
       STATUS      current





       INDEX    { rptrAddrTrackGroupIndex, rptrAddrTrackPortIndex }
       ::= { rptrAddrTrackTable 1 }

   RptrAddrTrackEntry ::=
       SEQUENCE {
           rptrAddrTrackGroupIndex
               INTEGER,
           rptrAddrTrackPortIndex
               INTEGER,
           rptrAddrTrackLastSourceAddress     -- DEPRECATED OBJECT
               MacAddress,
           rptrAddrTrackSourceAddrChanges
               Counter32,
           rptrAddrTrackNewLastSrcAddress
               OptMacAddr,
           rptrAddrTrackCapacity
               Integer32
       }

   rptrAddrTrackGroupIndex OBJECT-TYPE
       SYNTAX      INTEGER (1..2147483647)
       MAX-ACCESS  read-only
       STATUS      current
       ::= { rptrAddrTrackEntry 1 }

   rptrAddrTrackPortIndex OBJECT-TYPE
       SYNTAX      INTEGER (1..2147483647)
       MAX-ACCESS  read-only
       STATUS      current
       ::= { rptrAddrTrackEntry 2 }

   rptrAddrTrackLastSourceAddress OBJECT-TYPE
       SYNTAX      MacAddress
       MAX-ACCESS  read-only
       STATUS      deprecated
       ::= { rptrAddrTrackEntry 3 }

   rptrAddrTrackSourceAddrChanges OBJECT-TYPE
       SYNTAX      Counter32
       MAX-ACCESS  read-only
       STATUS      current
       ::= { rptrAddrTrackEntry 4 }

   rptrAddrTrackNewLastSrcAddress OBJECT-TYPE
       SYNTAX      OptMacAddr
       MAX-ACCESS  read-only
       STATUS      current





       ::= { rptrAddrTrackEntry 5 }

   rptrAddrTrackCapacity OBJECT-TYPE
       SYNTAX      Integer32
       MAX-ACCESS  read-only
       STATUS      current
       ::= { rptrAddrTrackEntry 6 }



   rptrExtAddrTrackTable OBJECT-TYPE
       SYNTAX      SEQUENCE OF RptrExtAddrTrackEntry
       MAX-ACCESS  not-accessible
       STATUS      current
       ::= { rptrAddrTrackPortInfo 2 }

   rptrExtAddrTrackEntry OBJECT-TYPE
       SYNTAX      RptrExtAddrTrackEntry





       MAX-ACCESS  not-accessible
       STATUS      current
       INDEX       { rptrAddrTrackGroupIndex,
                     rptrAddrTrackPortIndex,
                     rptrExtAddrTrackMacIndex }
       ::= { rptrExtAddrTrackTable 1 }

   RptrExtAddrTrackEntry ::= SEQUENCE {
       rptrExtAddrTrackMacIndex Integer32,
       rptrExtAddrTrackSourceAddress MacAddress
       }

   rptrExtAddrTrackMacIndex OBJECT-TYPE
       SYNTAX      Integer32 (1..2147483647)
       MAX-ACCESS  read-only
       STATUS      current
       ::= { rptrExtAddrTrackEntry 1 }

   rptrExtAddrTrackSourceAddress OBJECT-TYPE
       SYNTAX      MacAddress
       MAX-ACCESS  read-only
       STATUS      current
       ::= { rptrExtAddrTrackEntry 2 }











   rptrTopNPortControlTable OBJECT-TYPE
       SYNTAX      SEQUENCE OF RptrTopNPortControlEntry
       MAX-ACCESS  not-accessible
       STATUS      current
       ::= { rptrTopNPortInfo 1 }

   rptrTopNPortControlEntry OBJECT-TYPE
       SYNTAX      RptrTopNPortControlEntry
       MAX-ACCESS  not-accessible
       STATUS      current
       INDEX    { rptrTopNPortControlIndex }
       ::= { rptrTopNPortControlTable 1 }

   RptrTopNPortControlEntry ::= SEQUENCE {





       rptrTopNPortControlIndex
           Integer32,
       rptrTopNPortRepeaterId
           Integer32,
       rptrTopNPortRateBase
           INTEGER,
       rptrTopNPortTimeRemaining
           Integer32,
       rptrTopNPortDuration
           Integer32,
       rptrTopNPortRequestedSize
           Integer32,
       rptrTopNPortGrantedSize
           Integer32,
       rptrTopNPortStartTime
           TimeStamp,
       rptrTopNPortOwner
           OwnerString,
       rptrTopNPortRowStatus
           RowStatus
   }

   rptrTopNPortControlIndex OBJECT-TYPE
       SYNTAX      Integer32 (1 .. 65535)
       MAX-ACCESS  read-only
       STATUS      current
       ::= { rptrTopNPortControlEntry 1 }

   rptrTopNPortRepeaterId OBJECT-TYPE
       SYNTAX      Integer32 (0..2147483647)
       MAX-ACCESS  read-create
       STATUS      current
       ::= { rptrTopNPortControlEntry 2 }

   rptrTopNPortRateBase OBJECT-TYPE
       SYNTAX      INTEGER  {
                     readableFrames(1),
                     readableOctets(2),
                     fcsErrors(3),
                     alignmentErrors(4),
                     frameTooLongs(5),
                     shortEvents(6),
                     runts(7),
                     collisions(8),
                     lateEvents(9),
                     veryLongEvents(10),
                     dataRateMismatches(11),
                     autoPartitions(12),
                     totalErrors(13),
                     isolates(14),
                     symbolErrors(15)
                   }
       MAX-ACCESS  read-create
       STATUS      current
       ::= { rptrTopNPortControlEntry 3 }

   rptrTopNPortTimeRemaining OBJECT-TYPE
       SYNTAX      Integer32 (0..2147483647)
       MAX-ACCESS  read-create
       STATUS      current





       DEFVAL { 0 }
       ::= { rptrTopNPortControlEntry 4 }

   rptrTopNPortDuration OBJECT-TYPE
       SYNTAX      Integer32 (0..2147483647)
       MAX-ACCESS  read-only
       STATUS      current





        ::= { rptrTopNPortControlEntry 5 }

   rptrTopNPortRequestedSize OBJECT-TYPE
       SYNTAX      Integer32
       MAX-ACCESS  read-create
       STATUS      current
       DEFVAL { 10 }
       ::= { rptrTopNPortControlEntry 6 }

   rptrTopNPortGrantedSize OBJECT-TYPE
       SYNTAX      Integer32 (0..65535)
       MAX-ACCESS  read-only
       STATUS      current
       ::= { rptrTopNPortControlEntry 7 }

   rptrTopNPortStartTime OBJECT-TYPE
       SYNTAX      TimeStamp
       MAX-ACCESS  read-only
       STATUS      current
       ::= { rptrTopNPortControlEntry 8 }

   rptrTopNPortOwner OBJECT-TYPE





       SYNTAX      OwnerString
       MAX-ACCESS  read-create
       STATUS      current
       ::= { rptrTopNPortControlEntry 9 }

   rptrTopNPortRowStatus OBJECT-TYPE
       SYNTAX      RowStatus
       MAX-ACCESS  read-create
       STATUS      current
       ::= { rptrTopNPortControlEntry 10 }



   rptrTopNPortTable OBJECT-TYPE
       SYNTAX      SEQUENCE OF RptrTopNPortEntry
       MAX-ACCESS  not-accessible
       STATUS      current
       ::= { rptrTopNPortInfo 2 }

   rptrTopNPortEntry OBJECT-TYPE
       SYNTAX      RptrTopNPortEntry
       MAX-ACCESS  not-accessible
       STATUS      current
       INDEX    { rptrTopNPortControlIndex,
                  rptrTopNPortIndex }
       ::= { rptrTopNPortTable 1 }

   RptrTopNPortEntry ::= SEQUENCE {
       rptrTopNPortIndex
           Integer32,
       rptrTopNPortGroupIndex
           Integer32,
       rptrTopNPortPortIndex
           Integer32,
       rptrTopNPortRate
           Gauge32
   }

   rptrTopNPortIndex OBJECT-TYPE
       SYNTAX      Integer32 (1..65535)
       MAX-ACCESS  read-only
       STATUS      current
       ::= { rptrTopNPortEntry 1 }

   rptrTopNPortGroupIndex OBJECT-TYPE
       SYNTAX      Integer32  (1..2147483647)
       MAX-ACCESS  read-only
       STATUS      current
       ::= { rptrTopNPortEntry 2 }

   rptrTopNPortPortIndex OBJECT-TYPE
       SYNTAX      Integer32 (1..2147483647)





       MAX-ACCESS  read-only
       STATUS      current
       ::= { rptrTopNPortEntry 3 }

   rptrTopNPortRate OBJECT-TYPE
       SYNTAX      Gauge32
       MAX-ACCESS  read-only
       STATUS      current
       ::= { rptrTopNPortEntry 4 }




   rptrHealth NOTIFICATION-TYPE
       OBJECTS     { rptrOperStatus }
       STATUS      deprecated
       ::= { snmpDot3RptrMgt 0 1 }

   rptrGroupChange NOTIFICATION-TYPE
       OBJECTS     { rptrGroupIndex }
       STATUS      deprecated
       ::= { snmpDot3RptrMgt 0 2 }

   rptrResetEvent NOTIFICATION-TYPE
       OBJECTS     { rptrOperStatus }
       STATUS      deprecated
       ::= { snmpDot3RptrMgt 0 3 }



   rptrInfoHealth NOTIFICATION-TYPE
       OBJECTS     { rptrInfoOperStatus }
       STATUS      current
       ::= { snmpDot3RptrMgt 0 4 }

   rptrInfoResetEvent NOTIFICATION-TYPE
       OBJECTS     { rptrInfoOperStatus }
       STATUS      current
       ::= { snmpDot3RptrMgt 0 5 }



   snmpRptrModConf
           OBJECT IDENTIFIER ::= { snmpRptrMod 1 }





     snmpRptrModCompls
           OBJECT IDENTIFIER ::= { snmpRptrModConf 1 }
     snmpRptrModObjGrps
           OBJECT IDENTIFIER ::= { snmpRptrModConf 2 }
     snmpRptrModNotGrps
           OBJECT IDENTIFIER ::= { snmpRptrModConf 3 }



   snmpRptrGrpBasic1516 OBJECT-GROUP
       OBJECTS     { rptrGroupCapacity,
                     rptrOperStatus,
                     rptrHealthText,
                     rptrReset,
                     rptrNonDisruptTest,
                     rptrTotalPartitionedPorts,

                     rptrGroupIndex,
                     rptrGroupDescr,
                     rptrGroupObjectID,
                     rptrGroupOperStatus,
                     rptrGroupLastOperStatusChange,
                     rptrGroupPortCapacity,

                     rptrPortGroupIndex,
                     rptrPortIndex,
                     rptrPortAdminStatus,
                     rptrPortAutoPartitionState,
                     rptrPortOperStatus }
       STATUS      deprecated
       ::= { snmpRptrModObjGrps 1 }

   snmpRptrGrpMonitor1516 OBJECT-GROUP
       OBJECTS     { rptrMonitorTransmitCollisions,

                     rptrMonitorGroupIndex,
                     rptrMonitorGroupTotalFrames,
                     rptrMonitorGroupTotalOctets,
                     rptrMonitorGroupTotalErrors,






                     rptrMonitorPortGroupIndex,
                     rptrMonitorPortIndex,
                     rptrMonitorPortReadableFrames,
                     rptrMonitorPortReadableOctets,
                     rptrMonitorPortFCSErrors,
                     rptrMonitorPortAlignmentErrors,
                     rptrMonitorPortFrameTooLongs,
                     rptrMonitorPortShortEvents,
                     rptrMonitorPortRunts,
                     rptrMonitorPortCollisions,
                     rptrMonitorPortLateEvents,
                     rptrMonitorPortVeryLongEvents,
                     rptrMonitorPortDataRateMismatches,
                     rptrMonitorPortAutoPartitions,
                     rptrMonitorPortTotalErrors }
       STATUS      deprecated
       ::= { snmpRptrModObjGrps 2 }

   snmpRptrGrpAddrTrack1368 OBJECT-GROUP
       OBJECTS     { rptrAddrTrackGroupIndex,
                     rptrAddrTrackPortIndex,
                     rptrAddrTrackLastSourceAddress,
                     rptrAddrTrackSourceAddrChanges }
       STATUS      obsolete
       ::= { snmpRptrModObjGrps 3 }

   snmpRptrGrpAddrTrack1516 OBJECT-GROUP
       OBJECTS     { rptrAddrTrackGroupIndex,
                     rptrAddrTrackPortIndex,
                     rptrAddrTrackLastSourceAddress,
                     rptrAddrTrackSourceAddrChanges,
                     rptrAddrTrackNewLastSrcAddress }
       STATUS      deprecated
       ::= { snmpRptrModObjGrps 4 }

   snmpRptrGrpBasic OBJECT-GROUP
       OBJECTS     { rptrGroupIndex,
                     rptrGroupObjectID,
                     rptrGroupOperStatus,
                     rptrGroupPortCapacity,

                     rptrPortGroupIndex,
                     rptrPortIndex,
                     rptrPortAdminStatus,
                     rptrPortAutoPartitionState,
                     rptrPortOperStatus,
                     rptrPortRptrId,

                     rptrInfoId,
                     rptrInfoRptrType,
                     rptrInfoOperStatus,
                     rptrInfoReset,
                     rptrInfoPartitionedPorts,
                     rptrInfoLastChange }
       STATUS      current
       ::= { snmpRptrModObjGrps 5 }

   snmpRptrGrpMonitor OBJECT-GROUP
       OBJECTS     { rptrMonitorPortGroupIndex,
                     rptrMonitorPortIndex,
                     rptrMonitorPortReadableFrames,
                     rptrMonitorPortReadableOctets,
                     rptrMonitorPortFCSErrors,
                     rptrMonitorPortAlignmentErrors,
                     rptrMonitorPortFrameTooLongs,
                     rptrMonitorPortShortEvents,
                     rptrMonitorPortRunts,
                     rptrMonitorPortCollisions,
                     rptrMonitorPortLateEvents,
                     rptrMonitorPortVeryLongEvents,
                     rptrMonitorPortDataRateMismatches,
                     rptrMonitorPortAutoPartitions,
                     rptrMonitorPortTotalErrors,





                     rptrMonitorPortLastChange,

                     rptrMonTxCollisions,
                     rptrMonTotalFrames,
                     rptrMonTotalErrors,
                     rptrMonTotalOctets }
       STATUS      current
       ::= { snmpRptrModObjGrps 6 }

   snmpRptrGrpMonitor100 OBJECT-GROUP
       OBJECTS     { rptrMonitorPortIsolates,
                     rptrMonitorPortSymbolErrors,
                     rptrMonitorPortUpper32Octets,

                     rptrMonUpper32TotalOctets }
       STATUS      current
       ::= { snmpRptrModObjGrps 7 }

   snmpRptrGrpMonitor100w64 OBJECT-GROUP
       OBJECTS     { rptrMonitorPortHCReadableOctets,
                     rptrMonHCTotalOctets }
       STATUS      current
       ::= { snmpRptrModObjGrps 8 }

   snmpRptrGrpAddrTrack OBJECT-GROUP
       OBJECTS     { rptrAddrTrackGroupIndex,
                     rptrAddrTrackPortIndex,
                     rptrAddrTrackSourceAddrChanges,
                     rptrAddrTrackNewLastSrcAddress,
                     rptrAddrTrackCapacity }
       STATUS      current





       ::= { snmpRptrModObjGrps 9 }

   snmpRptrGrpExtAddrTrack OBJECT-GROUP
       OBJECTS     { rptrExtAddrTrackMacIndex,
                     rptrExtAddrTrackSourceAddress }
       STATUS      current
       ::= { snmpRptrModObjGrps 10 }

   snmpRptrGrpRptrAddrSearch OBJECT-GROUP
       OBJECTS     { rptrAddrSearchLock,
                     rptrAddrSearchStatus,
                     rptrAddrSearchAddress,
                     rptrAddrSearchState,
                     rptrAddrSearchGroup,
                     rptrAddrSearchPort,
                     rptrAddrSearchOwner }
       STATUS      current
       ::= { snmpRptrModObjGrps 11 }

   snmpRptrGrpTopNPort OBJECT-GROUP
       OBJECTS     { rptrTopNPortControlIndex,
                     rptrTopNPortRepeaterId,
                     rptrTopNPortRateBase,
                     rptrTopNPortTimeRemaining,
                     rptrTopNPortDuration,
                     rptrTopNPortRequestedSize,
                     rptrTopNPortGrantedSize,
                     rptrTopNPortStartTime,
                     rptrTopNPortOwner,
                     rptrTopNPortRowStatus,
                     rptrTopNPortIndex,
                     rptrTopNPortGroupIndex,
                     rptrTopNPortPortIndex,
                     rptrTopNPortRate }
       STATUS      current
       ::= { snmpRptrModObjGrps 12 }







   snmpRptrModComplRFC1368 MODULE-COMPLIANCE
       STATUS      obsolete

       MODULE -- this module
           MANDATORY-GROUPS { snmpRptrGrpBasic1516 }

           GROUP snmpRptrGrpMonitor1516

           GROUP snmpRptrGrpAddrTrack1368

       ::= { snmpRptrModCompls 1 }

   snmpRptrModComplRFC1516 MODULE-COMPLIANCE
       STATUS      deprecated

       MODULE -- this module
           MANDATORY-GROUPS { snmpRptrGrpBasic1516 }

           GROUP snmpRptrGrpMonitor1516

           GROUP snmpRptrGrpAddrTrack1516





       ::= { snmpRptrModCompls 2 }

   snmpRptrModCompl MODULE-COMPLIANCE
       STATUS      current

       MODULE -- this module
           MANDATORY-GROUPS { snmpRptrGrpBasic,
                              snmpRptrGrpMonitor,
                              snmpRptrGrpAddrTrack }

           GROUP snmpRptrGrpMonitor100

           GROUP snmpRptrGrpMonitor100w64

           GROUP snmpRptrGrpExtAddrTrack

           GROUP snmpRptrGrpRptrAddrSearch

           GROUP snmpRptrGrpTopNPort

       ::= { snmpRptrModCompls 3 }


   END

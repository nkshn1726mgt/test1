RADIUS-DYNAUTH-CLIENT-MIB DEFINITIONS ::= BEGIN

   IMPORTS
          MODULE-IDENTITY, OBJECT-TYPE,
          Counter32, Gauge32, Integer32,
          mib-2, TimeTicks    FROM SNMPv2-SMI         -- [RFC2578]
          SnmpAdminString     FROM SNMP-FRAMEWORK-MIB -- [RFC3411]
          InetAddressType, InetAddress,
          InetPortNumber      FROM INET-ADDRESS-MIB   -- [RFC4001]
          MODULE-COMPLIANCE,
          OBJECT-GROUP        FROM SNMPv2-CONF;       -- [RFC2580]

   radiusDynAuthClientMIB MODULE-IDENTITY
          LAST-UPDATED "200608290000Z" -- 29 August 2006
          ORGANIZATION "IETF RADEXT Working Group"

          ::= { mib-2 145 }

   radiusDynAuthClientMIBObjects OBJECT IDENTIFIER ::=
                                         { radiusDynAuthClientMIB 1 }

   radiusDynAuthClientScalars    OBJECT IDENTIFIER ::=
                                  { radiusDynAuthClientMIBObjects 1 }

   radiusDynAuthClientDisconInvalidServerAddresses OBJECT-TYPE
          SYNTAX Counter32
          MAX-ACCESS read-only
          STATUS current
          ::= { radiusDynAuthClientScalars 1 }

   radiusDynAuthClientCoAInvalidServerAddresses OBJECT-TYPE
          SYNTAX Counter32
          MAX-ACCESS read-only
          STATUS current
          ::= { radiusDynAuthClientScalars 2 }

   radiusDynAuthServerTable OBJECT-TYPE
          SYNTAX SEQUENCE OF RadiusDynAuthServerEntry
          MAX-ACCESS not-accessible
          STATUS     current
          ::= { radiusDynAuthClientMIBObjects 2 }

   radiusDynAuthServerEntry OBJECT-TYPE
          SYNTAX     RadiusDynAuthServerEntry
          MAX-ACCESS not-accessible
          STATUS     current
          INDEX      { radiusDynAuthServerIndex }
          ::= { radiusDynAuthServerTable 1 }

   RadiusDynAuthServerEntry ::= SEQUENCE {
          radiusDynAuthServerIndex                     Integer32,
          radiusDynAuthServerAddressType               InetAddressType,
          radiusDynAuthServerAddress                   InetAddress,
          radiusDynAuthServerClientPortNumber          InetPortNumber,
          radiusDynAuthServerID                        SnmpAdminString,
          radiusDynAuthClientRoundTripTime             TimeTicks,
          radiusDynAuthClientDisconRequests            Counter32,





          radiusDynAuthClientDisconAuthOnlyRequests    Counter32,
          radiusDynAuthClientDisconRetransmissions     Counter32,
          radiusDynAuthClientDisconAcks                Counter32,
          radiusDynAuthClientDisconNaks                Counter32,
          radiusDynAuthClientDisconNakAuthOnlyRequest  Counter32,
          radiusDynAuthClientDisconNakSessNoContext    Counter32,
          radiusDynAuthClientMalformedDisconResponses  Counter32,
          radiusDynAuthClientDisconBadAuthenticators   Counter32,
          radiusDynAuthClientDisconPendingRequests     Gauge32,
          radiusDynAuthClientDisconTimeouts            Counter32,
          radiusDynAuthClientDisconPacketsDropped      Counter32,
          radiusDynAuthClientCoARequests               Counter32,
          radiusDynAuthClientCoAAuthOnlyRequest        Counter32,
          radiusDynAuthClientCoARetransmissions        Counter32,
          radiusDynAuthClientCoAAcks                   Counter32,
          radiusDynAuthClientCoANaks                   Counter32,
          radiusDynAuthClientCoANakAuthOnlyRequest     Counter32,
          radiusDynAuthClientCoANakSessNoContext       Counter32,
          radiusDynAuthClientMalformedCoAResponses     Counter32,
          radiusDynAuthClientCoABadAuthenticators      Counter32,
          radiusDynAuthClientCoAPendingRequests        Gauge32,
          radiusDynAuthClientCoATimeouts               Counter32,
          radiusDynAuthClientCoAPacketsDropped         Counter32,
          radiusDynAuthClientUnknownTypes              Counter32,
          radiusDynAuthClientCounterDiscontinuity      TimeTicks
   }


   radiusDynAuthServerIndex OBJECT-TYPE
          SYNTAX     Integer32 (1..2147483647)
          MAX-ACCESS not-accessible
          STATUS     current
          ::= { radiusDynAuthServerEntry 1 }

   radiusDynAuthServerAddressType OBJECT-TYPE
          SYNTAX     InetAddressType
          MAX-ACCESS read-only
          STATUS     current
          ::= { radiusDynAuthServerEntry 2 }





   radiusDynAuthServerAddress OBJECT-TYPE
          SYNTAX     InetAddress
          MAX-ACCESS read-only
          STATUS     current
          ::= { radiusDynAuthServerEntry 3 }

   radiusDynAuthServerClientPortNumber OBJECT-TYPE
          SYNTAX     InetPortNumber (1..65535)
          MAX-ACCESS read-only
          STATUS     current
          ::= { radiusDynAuthServerEntry 4 }


   radiusDynAuthServerID OBJECT-TYPE
          SYNTAX     SnmpAdminString
          MAX-ACCESS read-only
          STATUS     current
          ::= { radiusDynAuthServerEntry 5 }

   radiusDynAuthClientRoundTripTime OBJECT-TYPE
          SYNTAX     TimeTicks
          UNITS      "hundredths of a second"
          MAX-ACCESS read-only
          STATUS     current
          ::= { radiusDynAuthServerEntry 6 }






   radiusDynAuthClientDisconRequests OBJECT-TYPE
          SYNTAX     Counter32
          UNITS      "requests"
          MAX-ACCESS read-only
          STATUS     current
          ::= { radiusDynAuthServerEntry 7 }

   radiusDynAuthClientDisconAuthOnlyRequests OBJECT-TYPE
          SYNTAX     Counter32
          UNITS      "requests"
          MAX-ACCESS read-only
          STATUS     current
          ::= { radiusDynAuthServerEntry 8 }

   radiusDynAuthClientDisconRetransmissions OBJECT-TYPE
          SYNTAX     Counter32
          UNITS      "retransmissions"
          MAX-ACCESS read-only
          STATUS     current
          ::= { radiusDynAuthServerEntry 9 }

   radiusDynAuthClientDisconAcks  OBJECT-TYPE
          SYNTAX     Counter32
          UNITS      "replies"
          MAX-ACCESS read-only
          STATUS     current
          ::= { radiusDynAuthServerEntry 10 }

   radiusDynAuthClientDisconNaks OBJECT-TYPE
          SYNTAX     Counter32
          UNITS      "replies"
          MAX-ACCESS read-only
          STATUS     current
          ::= { radiusDynAuthServerEntry 11 }

   radiusDynAuthClientDisconNakAuthOnlyRequest OBJECT-TYPE
          SYNTAX     Counter32
          UNITS      "replies"
          MAX-ACCESS read-only
          STATUS     current
          ::= { radiusDynAuthServerEntry 12 }

   radiusDynAuthClientDisconNakSessNoContext OBJECT-TYPE
          SYNTAX     Counter32
          UNITS      "replies"
          MAX-ACCESS read-only
          STATUS     current
          ::= { radiusDynAuthServerEntry 13 }

   radiusDynAuthClientMalformedDisconResponses OBJECT-TYPE
          SYNTAX     Counter32
          UNITS      "replies"
          MAX-ACCESS read-only
          STATUS     current
          ::= { radiusDynAuthServerEntry 14 }

   radiusDynAuthClientDisconBadAuthenticators OBJECT-TYPE
          SYNTAX     Counter32
          UNITS      "replies"
          MAX-ACCESS read-only
          STATUS     current





          ::= { radiusDynAuthServerEntry 15 }

   radiusDynAuthClientDisconPendingRequests OBJECT-TYPE
          SYNTAX     Gauge32
          UNITS      "requests"
          MAX-ACCESS read-only
          STATUS     current
          ::= { radiusDynAuthServerEntry 16 }

   radiusDynAuthClientDisconTimeouts OBJECT-TYPE
          SYNTAX     Counter32
          UNITS      "timeouts"
          MAX-ACCESS read-only
          STATUS     current
          ::= { radiusDynAuthServerEntry 17 }

   radiusDynAuthClientDisconPacketsDropped OBJECT-TYPE





          SYNTAX     Counter32
          UNITS      "replies"
          MAX-ACCESS read-only
          STATUS     current
          ::= { radiusDynAuthServerEntry 18 }

   radiusDynAuthClientCoARequests OBJECT-TYPE
          SYNTAX     Counter32
          UNITS      "requests"
          MAX-ACCESS read-only
          STATUS     current
          ::= { radiusDynAuthServerEntry 19 }

   radiusDynAuthClientCoAAuthOnlyRequest OBJECT-TYPE
          SYNTAX     Counter32
          UNITS      "requests"
          MAX-ACCESS read-only
          STATUS     current





          ::= { radiusDynAuthServerEntry 20 }

   radiusDynAuthClientCoARetransmissions OBJECT-TYPE
          SYNTAX     Counter32
          UNITS      "retransmissions"
          MAX-ACCESS read-only
          STATUS     current
          ::= { radiusDynAuthServerEntry 21 }

   radiusDynAuthClientCoAAcks  OBJECT-TYPE
          SYNTAX     Counter32
          UNITS      "replies"
          MAX-ACCESS read-only
          STATUS     current
          ::= { radiusDynAuthServerEntry 22 }

   radiusDynAuthClientCoANaks OBJECT-TYPE
          SYNTAX     Counter32
          UNITS      "replies"
          MAX-ACCESS read-only
          STATUS     current
          ::= { radiusDynAuthServerEntry 23 }

   radiusDynAuthClientCoANakAuthOnlyRequest OBJECT-TYPE
          SYNTAX     Counter32
          UNITS      "replies"
          MAX-ACCESS read-only
          STATUS     current
          ::= { radiusDynAuthServerEntry 24 }

   radiusDynAuthClientCoANakSessNoContext OBJECT-TYPE
          SYNTAX     Counter32
          UNITS      "replies"
          MAX-ACCESS read-only
          STATUS     current
          ::= { radiusDynAuthServerEntry 25 }

   radiusDynAuthClientMalformedCoAResponses OBJECT-TYPE
          SYNTAX     Counter32
          UNITS      "replies"
          MAX-ACCESS read-only
          STATUS     current





          ::= { radiusDynAuthServerEntry 26 }

   radiusDynAuthClientCoABadAuthenticators OBJECT-TYPE
          SYNTAX     Counter32
          UNITS      "replies"
          MAX-ACCESS read-only
          STATUS     current
          ::= { radiusDynAuthServerEntry 27 }

   radiusDynAuthClientCoAPendingRequests OBJECT-TYPE
          SYNTAX     Gauge32
          UNITS      "requests"
          MAX-ACCESS read-only
          STATUS     current
          ::= { radiusDynAuthServerEntry 28 }

   radiusDynAuthClientCoATimeouts OBJECT-TYPE





          SYNTAX     Counter32
          UNITS      "timeouts"
          MAX-ACCESS read-only
          STATUS     current
          ::= { radiusDynAuthServerEntry 29 }

   radiusDynAuthClientCoAPacketsDropped OBJECT-TYPE
          SYNTAX     Counter32
          UNITS      "replies"
          MAX-ACCESS read-only
          STATUS     current
          ::= { radiusDynAuthServerEntry 30 }

   radiusDynAuthClientUnknownTypes OBJECT-TYPE
          SYNTAX     Counter32
          UNITS      "replies"
          MAX-ACCESS read-only
          STATUS     current





          ::= { radiusDynAuthServerEntry 31 }

   radiusDynAuthClientCounterDiscontinuity OBJECT-TYPE
          SYNTAX TimeTicks
          UNITS  "hundredths of a second"
          MAX-ACCESS read-only
          STATUS current
          ::= { radiusDynAuthServerEntry 32 }



   radiusDynAuthClientMIBConformance
          OBJECT IDENTIFIER ::= { radiusDynAuthClientMIB 2 }
   radiusDynAuthClientMIBCompliances
          OBJECT IDENTIFIER ::= { radiusDynAuthClientMIBConformance 1 }
   radiusDynAuthClientMIBGroups
          OBJECT IDENTIFIER ::= { radiusDynAuthClientMIBConformance 2 }

   radiusDynAuthClientMIBCompliance MODULE-COMPLIANCE
          STATUS  current
          MODULE  -- this module
          MANDATORY-GROUPS { radiusDynAuthClientMIBGroup }

          OBJECT             radiusDynAuthServerAddressType
          SYNTAX             InetAddressType { ipv4(1), ipv6(2) }

          OBJECT             radiusDynAuthServerAddress
          SYNTAX             InetAddress (SIZE(4|16))





          GROUP              radiusDynAuthClientAuthOnlyGroup


          GROUP              radiusDynAuthClientNoSessGroup

          ::= { radiusDynAuthClientMIBCompliances 1 }


   radiusDynAuthClientMIBGroup OBJECT-GROUP
          OBJECTS { radiusDynAuthClientDisconInvalidServerAddresses,
                    radiusDynAuthClientCoAInvalidServerAddresses,
                    radiusDynAuthServerAddressType,
                    radiusDynAuthServerAddress,
                    radiusDynAuthServerClientPortNumber,
                    radiusDynAuthServerID,
                    radiusDynAuthClientRoundTripTime,
                    radiusDynAuthClientDisconRequests,
                    radiusDynAuthClientDisconRetransmissions,
                    radiusDynAuthClientDisconAcks,
                    radiusDynAuthClientDisconNaks,
                    radiusDynAuthClientMalformedDisconResponses,
                    radiusDynAuthClientDisconBadAuthenticators,
                    radiusDynAuthClientDisconPendingRequests,
                    radiusDynAuthClientDisconTimeouts,
                    radiusDynAuthClientDisconPacketsDropped,
                    radiusDynAuthClientCoARequests,
                    radiusDynAuthClientCoARetransmissions,
                    radiusDynAuthClientCoAAcks,
                    radiusDynAuthClientCoANaks,
                    radiusDynAuthClientMalformedCoAResponses,
                    radiusDynAuthClientCoABadAuthenticators,
                    radiusDynAuthClientCoAPendingRequests,
                    radiusDynAuthClientCoATimeouts,
                    radiusDynAuthClientCoAPacketsDropped,
                    radiusDynAuthClientUnknownTypes,
                    radiusDynAuthClientCounterDiscontinuity
                  }
          STATUS  current





          ::= { radiusDynAuthClientMIBGroups 1 }

   radiusDynAuthClientAuthOnlyGroup OBJECT-GROUP
          OBJECTS { radiusDynAuthClientDisconAuthOnlyRequests,
                    radiusDynAuthClientDisconNakAuthOnlyRequest,
                    radiusDynAuthClientCoAAuthOnlyRequest,
                    radiusDynAuthClientCoANakAuthOnlyRequest
                  }
          STATUS  current
          ::= { radiusDynAuthClientMIBGroups 2 }

   radiusDynAuthClientNoSessGroup OBJECT-GROUP
          OBJECTS { radiusDynAuthClientDisconNakSessNoContext,
                    radiusDynAuthClientCoANakSessNoContext
                  }
          STATUS  current
          ::= { radiusDynAuthClientMIBGroups 3 }



   END

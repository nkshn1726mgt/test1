DOCS-CABLE-DEVICE-MIB DEFINITIONS ::= BEGIN

   IMPORTS
           MODULE-IDENTITY,
           OBJECT-TYPE,
           IpAddress,
           Unsigned32,
           Counter32,
           Integer32,
           zeroDotZero,
           mib-2
                   FROM SNMPv2-SMI           -- RFC 2578
           RowStatus,
           RowPointer,
           DateAndTime,
           TruthValue,
           StorageType
                   FROM SNMPv2-TC            -- RFC 2579
           InetAddressType,
           InetAddress
                   FROM INET-ADDRESS-MIB     -- RFC 4001
           OBJECT-GROUP,
           MODULE-COMPLIANCE
                   FROM SNMPv2-CONF          -- RFC 2580
           SnmpAdminString
                   FROM SNMP-FRAMEWORK-MIB   -- RFC 3411
           InterfaceIndexOrZero
                   FROM IF-MIB               -- RFC 2863
           ZeroBasedCounter32
                   FROM RMON2-MIB            -- RFC 4502
           diffServMIBDataPathGroup,
           diffServMIBClfrGroup,
           diffServMIBClfrElementGroup,
           diffServMIBMultiFieldClfrGroup,
           diffServMIBActionGroup,
           diffServMIBDscpMarkActGroup,
           diffServMIBCounterGroup,
           diffServMIBAlgDropGroup,





           diffServDataPathStatus,
           diffServClfrStatus,
           diffServClfrElementStatus,
           diffServMultiFieldClfrAddrType,
           diffServMultiFieldClfrSrcAddr,
           diffServMultiFieldClfrDstAddr,
           diffServAlgDropStatus,
           diffServDataPathStorage,
           diffServClfrStorage,
           diffServClfrElementStorage,
           diffServMultiFieldClfrStorage,
           diffServActionStorage,
           diffServCountActStorage,
           diffServAlgDropStorage,
           diffServAlgDropType
                   FROM DIFFSERV-MIB;        -- RFC 3289


   docsDev MODULE-IDENTITY
           LAST-UPDATED    "200612200000Z" -- December 20, 2006
           ORGANIZATION    "IETF IP over Cable Data Network
                            Working Group"




           ::= { mib-2 69 }

   docsDevMIBObjects  OBJECT IDENTIFIER ::= { docsDev 1 }

   docsDevBase OBJECT IDENTIFIER ::= { docsDevMIBObjects 1 }


   docsDevRole OBJECT-TYPE
           SYNTAX INTEGER {
               cm(1),
               cmtsActive(2),
               cmtsBackup(3)
           }
           MAX-ACCESS  read-only
           STATUS      current
           ::= { docsDevBase 1 }






   docsDevDateTime OBJECT-TYPE
           SYNTAX      DateAndTime
           MAX-ACCESS  read-write
           STATUS      current
           ::= { docsDevBase 2 }

   docsDevResetNow OBJECT-TYPE
           SYNTAX      TruthValue
           MAX-ACCESS  read-write
           STATUS      current
           ::= { docsDevBase 3 }

   docsDevSerialNumber OBJECT-TYPE
           SYNTAX      SnmpAdminString
           MAX-ACCESS  read-only
           STATUS      current
           ::= { docsDevBase 4 }

   docsDevSTPControl OBJECT-TYPE
           SYNTAX INTEGER {
               stEnabled(1),
               noStFilterBpdu(2),
               noStPassBpdu(3)
           }
           MAX-ACCESS  read-write
           STATUS      current
           DEFVAL { noStFilterBpdu }
           ::= { docsDevBase 5 }

   docsDevIgmpModeControl OBJECT-TYPE
           SYNTAX INTEGER {
               passive(1),
               active(2)
           }
           MAX-ACCESS  read-write
           STATUS      current
           DEFVAL { passive }
           ::= { docsDevBase 6 }

   docsDevMaxCpe OBJECT-TYPE
           SYNTAX      Unsigned32 (0..255)
           UNITS       "CPEs"
           MAX-ACCESS  read-only
           STATUS      current
           ::= { docsDevBase 7 }



   docsDevNmAccessTable OBJECT-TYPE
           SYNTAX      SEQUENCE OF DocsDevNmAccessEntry
           MAX-ACCESS  not-accessible
           STATUS      deprecated
           ::= { docsDevMIBObjects 2 }

   docsDevNmAccessEntry OBJECT-TYPE
           SYNTAX      DocsDevNmAccessEntry
           MAX-ACCESS  not-accessible
           STATUS      deprecated
           INDEX { docsDevNmAccessIndex }
           ::= {  docsDevNmAccessTable 1 }

   DocsDevNmAccessEntry ::= SEQUENCE {
               docsDevNmAccessIndex         Integer32,
               docsDevNmAccessIp            IpAddress,
               docsDevNmAccessIpMask        IpAddress,
               docsDevNmAccessCommunity     OCTET STRING,
               docsDevNmAccessControl       INTEGER,
               docsDevNmAccessInterfaces    OCTET STRING,
               docsDevNmAccessStatus        RowStatus,
               docsDevNmAccessTrapVersion   INTEGER
           }

   docsDevNmAccessIndex OBJECT-TYPE
           SYNTAX      Integer32 (1..2147483647)
           MAX-ACCESS  not-accessible
           STATUS      deprecated
           ::= { docsDevNmAccessEntry 1 }

   docsDevNmAccessIp OBJECT-TYPE
           SYNTAX      IpAddress
           MAX-ACCESS  read-create
           STATUS      deprecated
           DEFVAL { '00000000'h }
           ::= { docsDevNmAccessEntry 2 }

   docsDevNmAccessIpMask OBJECT-TYPE
           SYNTAX      IpAddress
           MAX-ACCESS  read-create
           STATUS      deprecated





           DEFVAL { '00000000'h }
           ::= { docsDevNmAccessEntry 3 }

   docsDevNmAccessCommunity OBJECT-TYPE
           SYNTAX      OCTET STRING
           MAX-ACCESS  read-create
           STATUS      deprecated
           DEFVAL { "public" }
           ::= { docsDevNmAccessEntry 4 }

   docsDevNmAccessControl OBJECT-TYPE
           SYNTAX         INTEGER {
               none(1),
               read(2),
               readWrite(3),
               roWithTraps(4),
               rwWithTraps(5),
               trapsOnly(6)
           }
           MAX-ACCESS  read-create
           STATUS      deprecated
           DEFVAL { read }
           ::= { docsDevNmAccessEntry 5 }


   docsDevNmAccessInterfaces OBJECT-TYPE
           SYNTAX      OCTET STRING (SIZE (1..32))
           MAX-ACCESS  read-create
           STATUS      deprecated
           ::= { docsDevNmAccessEntry 6 }

   docsDevNmAccessStatus OBJECT-TYPE
           SYNTAX      RowStatus
           MAX-ACCESS  read-create
           STATUS      deprecated
           ::= { docsDevNmAccessEntry 7 }

   docsDevNmAccessTrapVersion OBJECT-TYPE
           SYNTAX      INTEGER {





               disableSNMPv2trap(1),
               enableSNMPv2trap(2)
           }
           MAX-ACCESS  read-create
           STATUS      deprecated
           DEFVAL { disableSNMPv2trap }
           ::= { docsDevNmAccessEntry 8 }


   docsDevSoftware OBJECT IDENTIFIER ::= { docsDevMIBObjects 3 }

   docsDevSwServer OBJECT-TYPE
           SYNTAX      IpAddress
           MAX-ACCESS  read-write
           STATUS      deprecated
           ::= { docsDevSoftware 1 }

   docsDevSwFilename OBJECT-TYPE
           SYNTAX      SnmpAdminString (SIZE (0..64))
           MAX-ACCESS  read-write
           STATUS      current
           ::= { docsDevSoftware 2 }

   docsDevSwAdminStatus OBJECT-TYPE
           SYNTAX INTEGER {
               upgradeFromMgt(1),
               allowProvisioningUpgrade(2),
               ignoreProvisioningUpgrade(3)
           }
           MAX-ACCESS  read-write
           STATUS      current
           DEFVAL { allowProvisioningUpgrade }
           ::= { docsDevSoftware 3 }

   docsDevSwOperStatus OBJECT-TYPE
           SYNTAX INTEGER {
               inProgress(1),
               completeFromProvisioning(2),
               completeFromMgt(3),
               failed(4),
               other(5)
           }





           MAX-ACCESS  read-only
           STATUS      current
           ::= { docsDevSoftware 4 }

   docsDevSwCurrentVers OBJECT-TYPE
           SYNTAX      SnmpAdminString
           MAX-ACCESS  read-only
           STATUS      current
           ::= { docsDevSoftware 5 }

   docsDevSwServerAddressType OBJECT-TYPE
           SYNTAX      InetAddressType
           MAX-ACCESS  read-write
           STATUS      current
           ::= { docsDevSoftware 6 }

   docsDevSwServerAddress OBJECT-TYPE
           SYNTAX      InetAddress
           MAX-ACCESS  read-write
           STATUS      current
           ::= { docsDevSoftware 7 }

   docsDevSwServerTransportProtocol OBJECT-TYPE
           SYNTAX INTEGER {
               tftp(1),
               http(2)
           }
           MAX-ACCESS  read-write
           STATUS      current
           DEFVAL { tftp }
           ::= { docsDevSoftware 8 }


   docsDevServer OBJECT IDENTIFIER ::= { docsDevMIBObjects 4 }

   docsDevServerBootState OBJECT-TYPE
           SYNTAX INTEGER {
               operational(1),
               disabled(2),
               waitingForDhcpOffer(3),
               waitingForDhcpResponse(4),
               waitingForTimeServer(5),
               waitingForTftp(6),
               refusedByCmts(7),
               forwardingDenied(8),
               other(9),
               unknown(10)
           }
           MAX-ACCESS  read-only
           STATUS      current
           ::= { docsDevServer 1 }

   docsDevServerDhcp OBJECT-TYPE
           SYNTAX      IpAddress
           MAX-ACCESS  read-only
           STATUS      deprecated
           ::= { docsDevServer 2 }

   docsDevServerTime OBJECT-TYPE
           SYNTAX      IpAddress
           MAX-ACCESS  read-only
           STATUS      deprecated
           ::= { docsDevServer 3 }

   docsDevServerTftp OBJECT-TYPE
           SYNTAX      IpAddress
           MAX-ACCESS  read-only
           STATUS      deprecated
           ::= { docsDevServer 4 }

   docsDevServerConfigFile OBJECT-TYPE
           SYNTAX      SnmpAdminString
           MAX-ACCESS  read-only
           STATUS      current
           ::= { docsDevServer 5 }

   docsDevServerDhcpAddressType OBJECT-TYPE
           SYNTAX      InetAddressType
           MAX-ACCESS  read-only
           STATUS      current
           ::= { docsDevServer 6 }

   docsDevServerDhcpAddress OBJECT-TYPE
           SYNTAX      InetAddress
           MAX-ACCESS  read-only
           STATUS      current
           ::= { docsDevServer 7 }






   docsDevServerTimeAddressType OBJECT-TYPE
           SYNTAX      InetAddressType
           MAX-ACCESS  read-only
           STATUS      current
           ::= { docsDevServer 8 }

   docsDevServerTimeAddress OBJECT-TYPE
           SYNTAX      InetAddress
           MAX-ACCESS  read-only
           STATUS      current
           ::= { docsDevServer 9 }

   docsDevServerConfigTftpAddressType OBJECT-TYPE
           SYNTAX      InetAddressType
           MAX-ACCESS  read-only
           STATUS      current
           ::= { docsDevServer 10 }

   docsDevServerConfigTftpAddress OBJECT-TYPE
           SYNTAX      InetAddress





           MAX-ACCESS  read-only
           STATUS      current
           ::= { docsDevServer 11 }



   docsDevEvent OBJECT IDENTIFIER ::= { docsDevMIBObjects 5 }

   docsDevEvControl OBJECT-TYPE
           SYNTAX INTEGER {
               resetLog(1),
               useDefaultReporting(2)
           }
           MAX-ACCESS  read-write
           STATUS      current
           ::= { docsDevEvent 1 }

   docsDevEvSyslog OBJECT-TYPE
           SYNTAX      IpAddress
           MAX-ACCESS  read-write
           STATUS      deprecated
           ::= { docsDevEvent 2 }

   docsDevEvThrottleAdminStatus OBJECT-TYPE





           SYNTAX INTEGER {
               unconstrained(1),
               maintainBelowThreshold(2),
               stopAtThreshold(3),
               inhibited(4)
           }
           MAX-ACCESS  read-write
           STATUS      current
           DEFVAL { unconstrained }
           ::= { docsDevEvent 3 }

   docsDevEvThrottleInhibited OBJECT-TYPE
           SYNTAX      TruthValue
           MAX-ACCESS  read-only
           STATUS      deprecated





           ::= { docsDevEvent 4 }

   docsDevEvThrottleThreshold OBJECT-TYPE
           SYNTAX      Unsigned32
           UNITS       "events"
           MAX-ACCESS  read-write
           STATUS      current
           DEFVAL { 0 }
           ::= { docsDevEvent 5 }

   docsDevEvThrottleInterval OBJECT-TYPE
           SYNTAX      Integer32 (1..2147483647)
           UNITS       "seconds"
           MAX-ACCESS  read-write
           STATUS      current
           DEFVAL { 1 }
           ::= { docsDevEvent 6 }


   docsDevEvControlTable OBJECT-TYPE
           SYNTAX      SEQUENCE OF DocsDevEvControlEntry
           MAX-ACCESS  not-accessible
           STATUS      current
           ::= {  docsDevEvent 7 }

   docsDevEvControlEntry OBJECT-TYPE
           SYNTAX      DocsDevEvControlEntry
           MAX-ACCESS  not-accessible
           STATUS      current
           INDEX { docsDevEvPriority }
           ::= { docsDevEvControlTable 1 }

   DocsDevEvControlEntry ::= SEQUENCE {
               docsDevEvPriority        INTEGER,
               docsDevEvReporting       BITS
           }

   docsDevEvPriority OBJECT-TYPE
           SYNTAX INTEGER {
               emergency(1),
               alert(2),
               critical(3),
               error(4),
               warning(5),
               notice(6),
               information(7),
               debug(8)
           }
           MAX-ACCESS  not-accessible
           STATUS      current
           ::= { docsDevEvControlEntry 1 }

   docsDevEvReporting OBJECT-TYPE
           SYNTAX BITS {
               local(0),
               traps(1),
               syslog(2),
               localVolatile(8),
               stdInterface(9)
           }
           MAX-ACCESS  read-write
           STATUS      current
           ::= { docsDevEvControlEntry 2 }

   docsDevEventTable OBJECT-TYPE
           SYNTAX      SEQUENCE OF DocsDevEventEntry
           MAX-ACCESS  not-accessible
           STATUS      current
           ::= {  docsDevEvent 8 }

   docsDevEventEntry OBJECT-TYPE
           SYNTAX      DocsDevEventEntry
           MAX-ACCESS  not-accessible
           STATUS      current
           INDEX { docsDevEvIndex }
           ::= { docsDevEventTable 1 }

   DocsDevEventEntry ::= SEQUENCE {
               docsDevEvIndex           Integer32,
               docsDevEvFirstTime       DateAndTime,





               docsDevEvLastTime        DateAndTime,
               docsDevEvCounts          Counter32,
               docsDevEvLevel           INTEGER,
               docsDevEvId              Unsigned32,
               docsDevEvText            SnmpAdminString
           }

   docsDevEvIndex OBJECT-TYPE
           SYNTAX      Integer32 (1..2147483647)
           MAX-ACCESS  not-accessible
           STATUS      current
           ::= { docsDevEventEntry 1 }

   docsDevEvFirstTime OBJECT-TYPE
           SYNTAX      DateAndTime
           MAX-ACCESS  read-only
           STATUS      current
           ::= { docsDevEventEntry 2 }

   docsDevEvLastTime OBJECT-TYPE
           SYNTAX      DateAndTime
           MAX-ACCESS  read-only
           STATUS      current
           ::= { docsDevEventEntry 3 }

   docsDevEvCounts OBJECT-TYPE
           SYNTAX      Counter32
           UNITS       "events"





           MAX-ACCESS  read-only
           STATUS      current
           ::= { docsDevEventEntry 4 }
   docsDevEvLevel OBJECT-TYPE
           SYNTAX INTEGER {
               emergency(1),
               alert(2),
               critical(3),
               error(4),
               warning(5),
               notice(6),
               information(7),
               debug(8)
           }
           MAX-ACCESS  read-only
           STATUS      current
           ::= { docsDevEventEntry 5 }


   docsDevEvId OBJECT-TYPE
           SYNTAX      Unsigned32
           MAX-ACCESS  read-only
           STATUS      current
           ::= { docsDevEventEntry 6 }

   docsDevEvText OBJECT-TYPE
           SYNTAX      SnmpAdminString
           MAX-ACCESS  read-only
           STATUS      current
           ::= { docsDevEventEntry 7 }

   docsDevEvSyslogAddressType OBJECT-TYPE
           SYNTAX      InetAddressType
           MAX-ACCESS  read-write
           STATUS      current
           DEFVAL { unknown }
           ::= { docsDevEvent 9 }






   docsDevEvSyslogAddress OBJECT-TYPE
           SYNTAX      InetAddress
           MAX-ACCESS  read-write
           STATUS      current
           ::= { docsDevEvent 10 }

   docsDevEvThrottleThresholdExceeded OBJECT-TYPE
           SYNTAX TruthValue
           MAX-ACCESS read-only
           STATUS current
           ::= { docsDevEvent 11 }


   docsDevFilter OBJECT IDENTIFIER ::= { docsDevMIBObjects 6 }

   docsDevFilterLLCUnmatchedAction OBJECT-TYPE
           SYNTAX INTEGER {
               discard(1),
               accept(2)
           }
           MAX-ACCESS  read-write
           STATUS      current
           DEFVAL { accept }
           ::= { docsDevFilter 1 }

   docsDevFilterLLCTable OBJECT-TYPE
           SYNTAX      SEQUENCE OF DocsDevFilterLLCEntry
           MAX-ACCESS  not-accessible
           STATUS      current
           ::= { docsDevFilter 2 }

   docsDevFilterLLCEntry OBJECT-TYPE
           SYNTAX      DocsDevFilterLLCEntry
           MAX-ACCESS  not-accessible
           STATUS      current
           INDEX { docsDevFilterLLCIndex }
           ::= { docsDevFilterLLCTable 1 }

   DocsDevFilterLLCEntry ::= SEQUENCE {
               docsDevFilterLLCIndex               Integer32,
               docsDevFilterLLCStatus              RowStatus,
               docsDevFilterLLCIfIndex             InterfaceIndexOrZero,
               docsDevFilterLLCProtocolType        INTEGER,
               docsDevFilterLLCProtocol            Integer32,
               docsDevFilterLLCMatches             Counter32
           }





   docsDevFilterLLCIndex OBJECT-TYPE
           SYNTAX      Integer32 (1..2147483647)
           MAX-ACCESS  not-accessible
           STATUS      current
           ::= { docsDevFilterLLCEntry 1 }
   docsDevFilterLLCStatus OBJECT-TYPE
           SYNTAX      RowStatus
           MAX-ACCESS  read-create
           STATUS      current
           ::= { docsDevFilterLLCEntry 2}

   docsDevFilterLLCIfIndex OBJECT-TYPE
           SYNTAX      InterfaceIndexOrZero
           MAX-ACCESS  read-create
           STATUS      current
           ::= { docsDevFilterLLCEntry 3 }






   docsDevFilterLLCProtocolType OBJECT-TYPE
           SYNTAX INTEGER {
               ethertype(1),
               dsap(2)
           }
           MAX-ACCESS  read-create
           STATUS      current
           DEFVAL { ethertype }
           ::= { docsDevFilterLLCEntry 4 }

   docsDevFilterLLCProtocol OBJECT-TYPE
           SYNTAX      Integer32 (0..65535)
           MAX-ACCESS  read-create
           STATUS      current
           DEFVAL { 0 }
           ::= { docsDevFilterLLCEntry 5 }

   docsDevFilterLLCMatches OBJECT-TYPE
           SYNTAX      Counter32
           UNITS       "matches"
           MAX-ACCESS  read-only
           STATUS      current
           ::= { docsDevFilterLLCEntry 6 }


   docsDevFilterIpDefault OBJECT-TYPE
           SYNTAX INTEGER {
               discard(1),
               accept(2)
           }
           MAX-ACCESS  read-write





           STATUS      deprecated
           DEFVAL { accept }
           ::= { docsDevFilter 3 }

   docsDevFilterIpTable OBJECT-TYPE
           SYNTAX      SEQUENCE OF DocsDevFilterIpEntry
           MAX-ACCESS  not-accessible
           STATUS      deprecated
           ::= { docsDevFilter 4 }

   docsDevFilterIpEntry OBJECT-TYPE
           SYNTAX      DocsDevFilterIpEntry
           MAX-ACCESS  not-accessible
           STATUS      deprecated
           INDEX { docsDevFilterIpIndex }
           ::= { docsDevFilterIpTable 1 }

   DocsDevFilterIpEntry ::= SEQUENCE {
               docsDevFilterIpIndex             Integer32,
               docsDevFilterIpStatus            RowStatus,
               docsDevFilterIpControl           INTEGER,





               docsDevFilterIpIfIndex           InterfaceIndexOrZero,
               docsDevFilterIpDirection         INTEGER,
               docsDevFilterIpBroadcast         TruthValue,
               docsDevFilterIpSaddr             IpAddress,
               docsDevFilterIpSmask             IpAddress,
               docsDevFilterIpDaddr             IpAddress,
               docsDevFilterIpDmask             IpAddress,
               docsDevFilterIpProtocol          Integer32,
               docsDevFilterIpSourcePortLow     Integer32,
               docsDevFilterIpSourcePortHigh    Integer32,
               docsDevFilterIpDestPortLow       Integer32,
               docsDevFilterIpDestPortHigh      Integer32,
               docsDevFilterIpMatches           ZeroBasedCounter32,
               docsDevFilterIpTos               OCTET STRING,
               docsDevFilterIpTosMask           OCTET STRING,
               docsDevFilterIpContinue          TruthValue,
               docsDevFilterIpPolicyId          Integer32
           }

   docsDevFilterIpIndex OBJECT-TYPE
           SYNTAX      Integer32 (1..2147483647)
           MAX-ACCESS  not-accessible
           STATUS      deprecated
           ::= { docsDevFilterIpEntry 1 }

   docsDevFilterIpStatus OBJECT-TYPE
           SYNTAX      RowStatus
           MAX-ACCESS  read-create
           STATUS      deprecated
           ::= { docsDevFilterIpEntry 2 }






   docsDevFilterIpControl OBJECT-TYPE
           SYNTAX INTEGER {
               discard(1),
               accept(2),
               policy(3)
           }
           MAX-ACCESS  read-create
           STATUS      deprecated
           DEFVAL { discard }
           ::= { docsDevFilterIpEntry 3 }

   docsDevFilterIpIfIndex OBJECT-TYPE
           SYNTAX      InterfaceIndexOrZero
           MAX-ACCESS  read-create
           STATUS      deprecated
           ::= { docsDevFilterIpEntry 4 }

   docsDevFilterIpDirection OBJECT-TYPE





           SYNTAX INTEGER {
               inbound(1),
               outbound(2),
               both(3)
           }
           MAX-ACCESS  read-create
           STATUS      deprecated
           DEFVAL { inbound }
           ::= { docsDevFilterIpEntry 5 }

   docsDevFilterIpBroadcast OBJECT-TYPE
           SYNTAX      TruthValue
           MAX-ACCESS  read-create
           STATUS      deprecated
           DEFVAL { false }
           ::= { docsDevFilterIpEntry 6 }

   docsDevFilterIpSaddr OBJECT-TYPE
           SYNTAX      IpAddress
           MAX-ACCESS  read-create
           STATUS      deprecated
           DEFVAL { '00000000'h }
           ::= { docsDevFilterIpEntry 7 }

   docsDevFilterIpSmask OBJECT-TYPE
           SYNTAX      IpAddress
           MAX-ACCESS  read-create
           STATUS      deprecated
           DEFVAL { '00000000'h }





           ::= { docsDevFilterIpEntry 8 }

   docsDevFilterIpDaddr OBJECT-TYPE
           SYNTAX      IpAddress
           MAX-ACCESS  read-create
           STATUS      deprecated
           DEFVAL { '00000000'h }
           ::= { docsDevFilterIpEntry 9 }

   docsDevFilterIpDmask OBJECT-TYPE
           SYNTAX      IpAddress
           MAX-ACCESS  read-create
           STATUS      deprecated
           DEFVAL { '00000000'h }
           ::= { docsDevFilterIpEntry 10 }

   docsDevFilterIpProtocol OBJECT-TYPE
           SYNTAX Integer32 (0..256)
           MAX-ACCESS  read-create
           STATUS      deprecated
           DEFVAL { 256 }
           ::= { docsDevFilterIpEntry 11 }

   docsDevFilterIpSourcePortLow OBJECT-TYPE
           SYNTAX      Integer32 (0..65535)
           MAX-ACCESS  read-create
           STATUS      deprecated
           DEFVAL { 0 }
           ::= { docsDevFilterIpEntry 12 }

   docsDevFilterIpSourcePortHigh OBJECT-TYPE
           SYNTAX      Integer32 (0..65535)
           MAX-ACCESS  read-create
           STATUS      deprecated
           DEFVAL { 65535 }
           ::= { docsDevFilterIpEntry 13 }

   docsDevFilterIpDestPortLow OBJECT-TYPE
           SYNTAX      Integer32 (0..65535)
           MAX-ACCESS  read-create
           STATUS      deprecated
           DEFVAL { 0 }
           ::= { docsDevFilterIpEntry 14 }

   docsDevFilterIpDestPortHigh OBJECT-TYPE
           SYNTAX      Integer32 (0..65535)
           MAX-ACCESS  read-create
           STATUS      deprecated
           DEFVAL { 65535 }
           ::= { docsDevFilterIpEntry 15 }

   docsDevFilterIpMatches OBJECT-TYPE
           SYNTAX      ZeroBasedCounter32
           UNITS       "matches"
           MAX-ACCESS  read-only





           STATUS      deprecated
           ::= { docsDevFilterIpEntry 16 }

   docsDevFilterIpTos  OBJECT-TYPE
           SYNTAX      OCTET STRING (SIZE (1))
           MAX-ACCESS  read-create
           STATUS      deprecated
           DEFVAL { '00'h }
           ::= { docsDevFilterIpEntry 17 }

   docsDevFilterIpTosMask OBJECT-TYPE
           SYNTAX      OCTET STRING (SIZE (1))
           MAX-ACCESS  read-create
           STATUS      deprecated
           DEFVAL { '00'h }
           ::= { docsDevFilterIpEntry 18 }

   docsDevFilterIpContinue OBJECT-TYPE
           SYNTAX      TruthValue
           MAX-ACCESS  read-create
           STATUS      deprecated
           DEFVAL { false }
           ::= { docsDevFilterIpEntry 19 }

   docsDevFilterIpPolicyId OBJECT-TYPE
           SYNTAX      Integer32 (0..2147483647)
           MAX-ACCESS  read-create
           STATUS      deprecated
           DEFVAL { 0 }
           ::= { docsDevFilterIpEntry 20 }


   docsDevFilterPolicyTable OBJECT-TYPE
           SYNTAX      SEQUENCE OF DocsDevFilterPolicyEntry
           MAX-ACCESS  not-accessible
           STATUS      deprecated
           ::= { docsDevFilter 5 }

   docsDevFilterPolicyEntry OBJECT-TYPE
           SYNTAX      DocsDevFilterPolicyEntry
           MAX-ACCESS  not-accessible
           STATUS      deprecated
           INDEX { docsDevFilterPolicyIndex }
           ::= { docsDevFilterPolicyTable 1 }

   DocsDevFilterPolicyEntry ::= SEQUENCE {
               docsDevFilterPolicyIndex   Integer32,
               docsDevFilterPolicyId      Integer32,
               docsDevFilterPolicyStatus  RowStatus,
               docsDevFilterPolicyPtr     RowPointer
           }

   docsDevFilterPolicyIndex OBJECT-TYPE
           SYNTAX      Integer32 (1..2147483647)
           MAX-ACCESS  not-accessible
           STATUS      deprecated
           ::= { docsDevFilterPolicyEntry 1 }

   docsDevFilterPolicyId OBJECT-TYPE
           SYNTAX      Integer32 (0..2147483647)
           MAX-ACCESS  read-create
           STATUS      deprecated
           ::= { docsDevFilterPolicyEntry 2 }






   docsDevFilterPolicyStatus OBJECT-TYPE
           SYNTAX      RowStatus
           MAX-ACCESS  read-create
           STATUS      deprecated
           ::= { docsDevFilterPolicyEntry 5 }

   docsDevFilterPolicyPtr OBJECT-TYPE
           SYNTAX      RowPointer
           MAX-ACCESS  read-create
           STATUS      deprecated
           DEFVAL { zeroDotZero }
           ::= { docsDevFilterPolicyEntry 6 }


   docsDevFilterTosTable OBJECT-TYPE
           SYNTAX      SEQUENCE OF DocsDevFilterTosEntry
           MAX-ACCESS  not-accessible
           STATUS      deprecated
           ::= { docsDevFilter 6 }

   docsDevFilterTosEntry OBJECT-TYPE
           SYNTAX      DocsDevFilterTosEntry
           MAX-ACCESS  not-accessible
           STATUS      deprecated
           INDEX { docsDevFilterTosIndex }
           ::= { docsDevFilterTosTable 1 }

   DocsDevFilterTosEntry ::= SEQUENCE {
               docsDevFilterTosIndex   Integer32,
               docsDevFilterTosStatus  RowStatus,
               docsDevFilterTosAndMask OCTET STRING,
               docsDevFilterTosOrMask  OCTET STRING
           }

   docsDevFilterTosIndex OBJECT-TYPE
           SYNTAX      Integer32 (1..2147483647)
           MAX-ACCESS  not-accessible
           STATUS      deprecated





           ::= { docsDevFilterTosEntry 1 }

   docsDevFilterTosStatus OBJECT-TYPE
           SYNTAX      RowStatus
           MAX-ACCESS  read-create
           STATUS      deprecated
           ::= { docsDevFilterTosEntry 2 }

   docsDevFilterTosAndMask OBJECT-TYPE
           SYNTAX      OCTET STRING (SIZE (1))
           MAX-ACCESS  read-create
           STATUS      deprecated
           DEFVAL { 'ff'h }
           ::= { docsDevFilterTosEntry 3 }

   docsDevFilterTosOrMask OBJECT-TYPE
           SYNTAX      OCTET STRING (SIZE (1))
           MAX-ACCESS  read-create
           STATUS      deprecated
           DEFVAL { '00'h }
           ::= { docsDevFilterTosEntry 4 }


   docsDevCpe OBJECT IDENTIFIER ::= { docsDevMIBObjects 7 }

   docsDevCpeEnroll OBJECT-TYPE
           SYNTAX      INTEGER {
               none(1),
               any(2)





           }
           MAX-ACCESS  read-write
           STATUS      current
           DEFVAL { any }
           ::= { docsDevCpe 1 }

   docsDevCpeIpMax OBJECT-TYPE
           SYNTAX      Integer32 (-1..2147483647)
           MAX-ACCESS  read-write
           STATUS      current
           DEFVAL { -1 }
           ::= { docsDevCpe 2 }

   docsDevCpeTable OBJECT-TYPE
           SYNTAX      SEQUENCE OF DocsDevCpeEntry
           MAX-ACCESS  not-accessible
           STATUS      deprecated
           ::= { docsDevCpe 3 }

   docsDevCpeEntry OBJECT-TYPE
           SYNTAX      DocsDevCpeEntry
           MAX-ACCESS  not-accessible
           STATUS      deprecated
           INDEX   { docsDevCpeIp }
           ::= {docsDevCpeTable 1 }

   DocsDevCpeEntry ::= SEQUENCE {
               docsDevCpeIp      IpAddress,
               docsDevCpeSource  INTEGER,
               docsDevCpeStatus  RowStatus
           }

   docsDevCpeIp OBJECT-TYPE
           SYNTAX      IpAddress
           MAX-ACCESS  not-accessible
           STATUS      deprecated





           ::= { docsDevCpeEntry 1 }

   docsDevCpeSource OBJECT-TYPE
           SYNTAX      INTEGER {
               other(1),
               manual(2),
               learned(3)
           }

           MAX-ACCESS  read-only
           STATUS      deprecated
           ::= { docsDevCpeEntry 2 }

   docsDevCpeStatus OBJECT-TYPE
           SYNTAX  RowStatus
           MAX-ACCESS  read-create
           STATUS  deprecated
           ::= { docsDevCpeEntry 3 }


   docsDevCpeInetTable OBJECT-TYPE
           SYNTAX      SEQUENCE OF DocsDevCpeInetEntry
           MAX-ACCESS  not-accessible
           STATUS      current
           ::= { docsDevCpe 4 }

   docsDevCpeInetEntry OBJECT-TYPE
           SYNTAX      DocsDevCpeInetEntry
           MAX-ACCESS  not-accessible
           STATUS      current
           INDEX   { docsDevCpeInetType, docsDevCpeInetAddr }
           ::= { docsDevCpeInetTable 1 }

   DocsDevCpeInetEntry ::= SEQUENCE {
               docsDevCpeInetType      InetAddressType,
               docsDevCpeInetAddr      InetAddress,
               docsDevCpeInetSource    INTEGER,
               docsDevCpeInetRowStatus RowStatus
           }






   docsDevCpeInetType OBJECT-TYPE
           SYNTAX      InetAddressType
           MAX-ACCESS  not-accessible
           STATUS      current
            ::= { docsDevCpeInetEntry 1 }

   docsDevCpeInetAddr OBJECT-TYPE
           SYNTAX      InetAddress
           MAX-ACCESS  not-accessible
           STATUS      current
           ::= { docsDevCpeInetEntry 2 }

   docsDevCpeInetSource OBJECT-TYPE
           SYNTAX      INTEGER {
               manual(2),
               learned(3)
           }
           MAX-ACCESS  read-only
           STATUS      current
           ::= { docsDevCpeInetEntry 3 }

   docsDevCpeInetRowStatus OBJECT-TYPE
           SYNTAX  RowStatus
           MAX-ACCESS  read-create
           STATUS  current





           ::= { docsDevCpeInetEntry 4 }



   docsDevNotification OBJECT IDENTIFIER   ::= { docsDev 2 }

   docsDevNotifications OBJECT IDENTIFIER   ::= { docsDev 0 }



   docsDevConformance  OBJECT IDENTIFIER   ::= { docsDev 3 }
   docsDevGroups       OBJECT IDENTIFIER   ::= { docsDevConformance 1 }
   docsDevCompliances  OBJECT IDENTIFIER   ::= { docsDevConformance 2 }

   docsDevBasicCompliance MODULE-COMPLIANCE
           STATUS  deprecated

   MODULE  -- docsDev


   GROUP docsDevBaseGroup

   GROUP docsDevEventGroup

   GROUP docsDevFilterGroup

   GROUP docsDevNmAccessGroup






   GROUP docsDevServerGroup

   GROUP docsDevSoftwareGroup

   GROUP docsDevCpeGroup

   OBJECT docsDevSTPControl
           MIN-ACCESS read-only

   OBJECT docsDevNmAccessIp

   OBJECT docsDevEvReporting
            MIN-ACCESS read-only
            ::= { docsDevCompliances 1 }

   docsDevBaseGroup OBJECT-GROUP
           OBJECTS {
                docsDevRole,
                docsDevDateTime,





                docsDevResetNow,
                docsDevSerialNumber,
                docsDevSTPControl
           }
           STATUS      current
           ::= { docsDevGroups 1 }

   docsDevNmAccessGroup OBJECT-GROUP
           OBJECTS {
                docsDevNmAccessIp,
                docsDevNmAccessIpMask,
                docsDevNmAccessCommunity,
                docsDevNmAccessControl,
                docsDevNmAccessInterfaces,
                docsDevNmAccessStatus
           }
           STATUS      deprecated
           ::= { docsDevGroups 2 }

   docsDevSoftwareGroup OBJECT-GROUP
           OBJECTS {
               docsDevSwServer,
               docsDevSwFilename,
               docsDevSwAdminStatus,
               docsDevSwOperStatus,
               docsDevSwCurrentVers
           }
           STATUS      deprecated





           ::= { docsDevGroups 3 }

   docsDevServerGroup OBJECT-GROUP
           OBJECTS {
               docsDevServerBootState,
               docsDevServerDhcp,
               docsDevServerTime,
               docsDevServerTftp,
               docsDevServerConfigFile
           }
           STATUS      deprecated
           ::= { docsDevGroups 4 }

   docsDevEventGroup OBJECT-GROUP
           OBJECTS {
               docsDevEvControl,
               docsDevEvSyslog,
               docsDevEvThrottleAdminStatus,
               docsDevEvThrottleInhibited,
               docsDevEvThrottleThreshold,
               docsDevEvThrottleInterval,
               docsDevEvReporting,
               docsDevEvFirstTime,
               docsDevEvLastTime,
               docsDevEvCounts,
               docsDevEvLevel,
               docsDevEvId,
               docsDevEvText
           }
           STATUS      deprecated
           ::= { docsDevGroups 5 }

   docsDevFilterGroup OBJECT-GROUP
           OBJECTS {
               docsDevFilterLLCUnmatchedAction,
               docsDevFilterIpDefault,
               docsDevFilterLLCStatus,
               docsDevFilterLLCIfIndex,
               docsDevFilterLLCProtocolType,
               docsDevFilterLLCProtocol,
               docsDevFilterLLCMatches,
               docsDevFilterIpControl,
               docsDevFilterIpIfIndex,
               docsDevFilterIpStatus,
               docsDevFilterIpDirection,
               docsDevFilterIpBroadcast,
               docsDevFilterIpSaddr,
               docsDevFilterIpSmask,
               docsDevFilterIpDaddr,
               docsDevFilterIpDmask,
               docsDevFilterIpProtocol,
               docsDevFilterIpSourcePortLow,
               docsDevFilterIpSourcePortHigh,
               docsDevFilterIpDestPortLow,
               docsDevFilterIpDestPortHigh,
               docsDevFilterIpMatches,
               docsDevFilterIpTos,
               docsDevFilterIpTosMask,
               docsDevFilterIpContinue,
               docsDevFilterIpPolicyId,
               docsDevFilterPolicyId,
               docsDevFilterPolicyStatus,
               docsDevFilterPolicyPtr,
               docsDevFilterTosStatus,
               docsDevFilterTosAndMask,
               docsDevFilterTosOrMask
           }
           STATUS      deprecated





           ::= { docsDevGroups 6 }

   docsDevCpeGroup OBJECT-GROUP
           OBJECTS {
              docsDevCpeEnroll,
              docsDevCpeIpMax,
              docsDevCpeSource,
              docsDevCpeStatus
           }
           STATUS      deprecated
           ::= { docsDevGroups 7 }


   docsDevGroupsV2       OBJECT IDENTIFIER  ::= { docsDevConformance 3 }
   docsDevCompliancesV2  OBJECT IDENTIFIER  ::= { docsDevConformance 4 }

   docsDevCmCompliance MODULE-COMPLIANCE
            STATUS  current

   MODULE DIFFSERV-MIB -- RFC 3289

   MANDATORY-GROUPS {
              diffServMIBDataPathGroup,
              diffServMIBClfrGroup,
              diffServMIBClfrElementGroup,
              diffServMIBMultiFieldClfrGroup,
              diffServMIBActionGroup,
              diffServMIBDscpMarkActGroup,
              diffServMIBCounterGroup,
              diffServMIBAlgDropGroup





              }

   OBJECT diffServDataPathStatus  -- same as RFC 3289
            SYNTAX RowStatus { active(1) }
            WRITE-SYNTAX RowStatus { createAndGo(4), destroy(6) }

   OBJECT diffServClfrStatus  -- same as RFC 3289
            SYNTAX RowStatus { active(1) }
            WRITE-SYNTAX RowStatus { createAndGo(4), destroy(6) }

   OBJECT diffServClfrElementStatus  -- same as RFC 3289
            SYNTAX RowStatus { active(1) }
            WRITE-SYNTAX RowStatus { createAndGo(4), destroy(6) }

   OBJECT diffServMultiFieldClfrAddrType
            SYNTAX  InetAddressType { ipv4(1) }

   OBJECT diffServMultiFieldClfrSrcAddr
            SYNTAX  InetAddress (SIZE(4))

   OBJECT diffServMultiFieldClfrDstAddr
            SYNTAX  InetAddress (SIZE(4))

   OBJECT diffServAlgDropStatus  -- same as RFC 3289
            SYNTAX RowStatus { active(1) }
            WRITE-SYNTAX RowStatus { createAndGo(4), destroy(6) }






   OBJECT diffServDataPathStorage
            SYNTAX StorageType { volatile(2) }

   OBJECT diffServClfrStorage
            SYNTAX StorageType { volatile(2) }

   OBJECT diffServClfrElementStorage
            SYNTAX StorageType { volatile(2) }

   OBJECT diffServMultiFieldClfrStorage
            SYNTAX StorageType { volatile(2) }

   OBJECT diffServActionStorage
            SYNTAX StorageType { volatile(2) }

   OBJECT diffServCountActStorage
            SYNTAX StorageType { volatile(2) }

   OBJECT diffServAlgDropStorage
            SYNTAX StorageType { volatile(2) }

   OBJECT diffServAlgDropType
            SYNTAX  INTEGER { alwaysDrop(5) }





   MODULE  -- docsDev

   MANDATORY-GROUPS {
              docsDevBaseGroup,
              docsDevBaseIgmpGroup,
              docsDevBaseMaxCpeGroup,
              docsDevSoftwareGroupV2,
              docsDevServerGroupV2,
              docsDevEventGroupV2,
              docsDevFilterLLCGroup
              }


   GROUP docsDevInetCpeGroup

   OBJECT docsDevDateTime
            MIN-ACCESS read-only

   OBJECT docsDevSTPControl
            SYNTAX INTEGER { noStFilterBpdu(2) }
            MIN-ACCESS read-only

   OBJECT docsDevIgmpModeControl
            SYNTAX INTEGER { passive(1) }
            MIN-ACCESS read-only

   OBJECT docsDevSwServerAddressType
            SYNTAX InetAddressType { ipv4(1) }

   OBJECT docsDevSwServerAddress
            SYNTAX  InetAddress (SIZE(4))





   OBJECT docsDevServerDhcpAddressType
            SYNTAX InetAddressType { ipv4(1) }

   OBJECT docsDevServerDhcpAddress
            SYNTAX  InetAddress (SIZE(4))

   OBJECT docsDevServerTimeAddressType
            SYNTAX InetAddressType { ipv4(1) }

   OBJECT docsDevServerTimeAddress
            SYNTAX  InetAddress (SIZE(4))

   OBJECT docsDevServerConfigTftpAddressType
            SYNTAX InetAddressType { ipv4(1) }

   OBJECT docsDevServerConfigTftpAddress
            SYNTAX  InetAddress (SIZE(4))

   OBJECT docsDevEvReporting
            MIN-ACCESS read-only

   OBJECT docsDevEvSyslogAddressType
            SYNTAX InetAddressType { ipv4(1) }






   OBJECT docsDevEvSyslogAddress
            SYNTAX  InetAddress (SIZE(4))

   OBJECT docsDevSwServerTransportProtocol
            SYNTAX INTEGER { tftp(1) }

            ::= { docsDevCompliancesV2 1 }

   docsDevCmtsCompliance MODULE-COMPLIANCE
            STATUS  current

   MODULE  -- docsDev


   GROUP docsDevBaseGroup

   GROUP docsDevBaseIgmpGroup

   GROUP docsDevBaseMaxCpeGroup

   GROUP docsDevSoftwareGroupV2

   GROUP docsDevServerGroupV2





   GROUP docsDevEventGroupV2

   GROUP docsDevFilterLLCGroup

   GROUP docsDevInetCpeGroup

   OBJECT docsDevDateTime
            MIN-ACCESS read-only

   OBJECT docsDevSTPControl
            SYNTAX INTEGER { noStFilterBpdu(2) }
            MIN-ACCESS read-only

   OBJECT docsDevIgmpModeControl
            SYNTAX INTEGER { passive(1) }
            MIN-ACCESS read-only

   OBJECT docsDevSwServerAddressType
            SYNTAX InetAddressType { ipv4(1) }

   OBJECT docsDevSwServerAddress
            SYNTAX  InetAddress (SIZE(4))

   OBJECT docsDevEvReporting





            MIN-ACCESS read-only

   OBJECT docsDevEvSyslogAddressType
            SYNTAX InetAddressType { ipv4(1) }

   OBJECT docsDevEvSyslogAddress
            SYNTAX  InetAddress (SIZE(4))

   OBJECT docsDevSwServerTransportProtocol
            SYNTAX INTEGER { tftp(1) }

            ::= { docsDevCompliancesV2 2 }

   docsDevBaseIgmpGroup OBJECT-GROUP
           OBJECTS {
                docsDevIgmpModeControl
           }
           STATUS      current
           ::= { docsDevGroupsV2 1 }

   docsDevBaseMaxCpeGroup OBJECT-GROUP
           OBJECTS {
                docsDevMaxCpe
           }
           STATUS      current
           ::= { docsDevGroupsV2 2 }

   docsDevNmAccessExtGroup OBJECT-GROUP
           OBJECTS {
                docsDevNmAccessTrapVersion





           }
           STATUS      deprecated
           ::= { docsDevGroupsV2 3 }

   docsDevSoftwareGroupV2 OBJECT-GROUP
           OBJECTS {
               docsDevSwFilename,
               docsDevSwAdminStatus,
               docsDevSwOperStatus,
               docsDevSwCurrentVers,
               docsDevSwServerAddressType,
               docsDevSwServerAddress,
               docsDevSwServerTransportProtocol
           }
           STATUS      current
           ::= { docsDevGroupsV2 4 }

   docsDevServerGroupV2 OBJECT-GROUP
           OBJECTS {
               docsDevServerBootState,
               docsDevServerDhcpAddressType,
               docsDevServerDhcpAddress,
               docsDevServerTimeAddressType,
               docsDevServerTimeAddress,
               docsDevServerConfigTftpAddressType,
               docsDevServerConfigTftpAddress,
               docsDevServerConfigFile
           }
           STATUS      current
           ::= { docsDevGroupsV2 5 }





   docsDevEventGroupV2 OBJECT-GROUP
           OBJECTS {
               docsDevEvControl,
               docsDevEvThrottleAdminStatus,
               docsDevEvThrottleThreshold,
               docsDevEvThrottleInterval,
               docsDevEvReporting,
               docsDevEvFirstTime,
               docsDevEvLastTime,
               docsDevEvCounts,
               docsDevEvLevel,
               docsDevEvId,
               docsDevEvText,
               docsDevEvSyslogAddressType,
               docsDevEvSyslogAddress,
               docsDevEvThrottleThresholdExceeded
           }
           STATUS      current
           ::= { docsDevGroupsV2 6 }

   docsDevFilterLLCGroup OBJECT-GROUP
           OBJECTS {
               docsDevFilterLLCUnmatchedAction,
               docsDevFilterLLCStatus,
               docsDevFilterLLCIfIndex,
               docsDevFilterLLCProtocolType,
               docsDevFilterLLCProtocol,
               docsDevFilterLLCMatches
           }
           STATUS      current
           ::= { docsDevGroupsV2 7 }

   docsDevInetCpeGroup OBJECT-GROUP
           OBJECTS {
              docsDevCpeEnroll,
              docsDevCpeIpMax,
              docsDevCpeInetSource,
              docsDevCpeInetRowStatus
           }
           STATUS     current





           ::= { docsDevGroupsV2 8 }

   END
